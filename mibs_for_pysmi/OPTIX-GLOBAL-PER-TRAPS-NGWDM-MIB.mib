--
-- OPTIX-SONET-DataPm-MIB.mib
-- MIB generated by MG-SOFT Visual MIB Builder Version 3.0 Build 253
-- Monday, March 06, 2006 at 10:26:16
--
            -- =================================================================
--  Copyright (C) 2006 by HUAWEI TECHNOLOGIES. All rights reserved
--
--  Description:This MIB describes the DataPmformance interface of Huawei SONET transmit
--  Reference:
--  Version: V1.00
--  History:
--     <author>,<date>,<contents>
-- =================================================================
--

    OPTIX-GLOBAL-PER-TRAPS-NGWDM-MIB DEFINITIONS ::= BEGIN

        IMPORTS
            DateAndTime, DisplayString
                FROM SNMPv2-TC
            MOD2Type, PerformanceEventType, ValidflagType, ObjType, DataPmEventType
                FROM OPTIX-GLOBAL-TC-MIB

            optixGlobalTrap,
            rptEvtNumber, rptAlmName, rptEvtNtfcnCde, rptEvtState, rptEvtStartTime, rptEvtEndTime,
            rptEvtSrvEff, rptEvtObjType, rptEvtPara, rptEvtValue
                FROM OPTIX-GLOBAL-TRAPS-MIB

            OBJECT-GROUP, MODULE-COMPLIANCE
                FROM SNMPv2-CONF
            Integer32, Unsigned32, OBJECT-TYPE, MODULE-IDENTITY
                FROM SNMPv2-SMI;


        optixTrapsPER OBJECT IDENTIFIER ::= { optixGlobalTrap 30 }
    --  1.3.6.1.4.1.2011.2.25.3.40.40.30.133
       perEvtfecCorrected0BitCount NOTIFICATION-TYPE
       OBJECTS { rptEvtPeriod, rptEvtValue, rptEvtVldty, rptEvtDateTime, rptEvtObjType, rptEvtParaLen, rptEvtPara}
       STATUS current
       DESCRIPTION
       "Trap of PerEvt: Forward Error Correction - Corrected 0 Bit Count"
       ::= { optixTrapsPER  133}


	--  1.3.6.1.4.1.2011.2.25.3.40.40.30.121
    perEvtEdtplmax NOTIFICATION-TYPE
    OBJECTS { rptEvtPeriod, rptEvtValue, rptEvtVldty, rptEvtDateTime, rptEvtObjType, rptEvtParaLen, rptEvtPara}
    STATUS current
    DESCRIPTION
    "Trap of PerEvt: perEvtEdtplmax."
    ::= { optixTrapsPER 121 }

--  1.3.6.1.4.1.2011.2.25.3.40.40.30.122
    perEvtEdtplmin NOTIFICATION-TYPE
    OBJECTS { rptEvtPeriod, rptEvtValue, rptEvtVldty, rptEvtDateTime, rptEvtObjType, rptEvtParaLen, rptEvtPara}
    STATUS current
    DESCRIPTION
    "Trap of PerEvt: perEvtEdtplmin."
    ::= { optixTrapsPER 122 }

--  1.3.6.1.4.1.2011.2.25.3.40.40.30.123
    perEvtEdtplcur NOTIFICATION-TYPE
    OBJECTS { rptEvtPeriod, rptEvtValue, rptEvtVldty, rptEvtDateTime, rptEvtObjType, rptEvtParaLen, rptEvtPara}
    STATUS current
    DESCRIPTION
    "Trap of PerEvt: perEvtEdtplcur."
    ::= { optixTrapsPER 123 }

--  1.3.6.1.4.1.2011.2.25.3.40.40.30.228
    perEvtPclswlmax NOTIFICATION-TYPE
    OBJECTS { rptEvtPeriod, rptEvtValue, rptEvtVldty, rptEvtDateTime, rptEvtObjType, rptEvtParaLen, rptEvtPara}
    STATUS current
    DESCRIPTION
    "Trap of PerEvt: perEvtPclswlmax."
    ::= { optixTrapsPER 228 }

--  1.3.6.1.4.1.2011.2.25.3.40.40.30.229
    perEvtPclswlmin NOTIFICATION-TYPE
    OBJECTS { rptEvtPeriod, rptEvtValue, rptEvtVldty, rptEvtDateTime, rptEvtObjType, rptEvtParaLen, rptEvtPara}
    STATUS current
    DESCRIPTION
    "Trap of PerEvt: perEvtPclswlmin."
    ::= { optixTrapsPER 229 }

--  1.3.6.1.4.1.2011.2.25.3.40.40.30.230
    perEvtPclswlcur NOTIFICATION-TYPE
    OBJECTS { rptEvtPeriod, rptEvtValue, rptEvtVldty, rptEvtDateTime, rptEvtObjType, rptEvtParaLen, rptEvtPara}
    STATUS current
    DESCRIPTION
    "Trap of PerEvt: perEvtPclswlcur."
    ::= { optixTrapsPER 230 }

--  1.3.6.1.4.1.2011.2.25.3.40.40.30.231
    perEvtPclswlomax NOTIFICATION-TYPE
    OBJECTS { rptEvtPeriod, rptEvtValue, rptEvtVldty, rptEvtDateTime, rptEvtObjType, rptEvtParaLen, rptEvtPara}
    STATUS current
    DESCRIPTION
    "Trap of PerEvt: perEvtPclswlomax."
    ::= { optixTrapsPER 231 }

--  1.3.6.1.4.1.2011.2.25.3.40.40.30.232
    perEvtPclswlomin NOTIFICATION-TYPE
    OBJECTS { rptEvtPeriod, rptEvtValue, rptEvtVldty, rptEvtDateTime, rptEvtObjType, rptEvtParaLen, rptEvtPara}
    STATUS current
    DESCRIPTION
    "Trap of PerEvt: perEvtPclswlomin."
    ::= { optixTrapsPER 232 }

--  1.3.6.1.4.1.2011.2.25.3.40.40.30.233
    perEvtPclswlocur NOTIFICATION-TYPE
    OBJECTS { rptEvtPeriod, rptEvtValue, rptEvtVldty, rptEvtDateTime, rptEvtObjType, rptEvtParaLen, rptEvtPara}
    STATUS current
    DESCRIPTION
    "Trap of PerEvt: perEvtPclswlocur."
    ::= { optixTrapsPER 233 }

--  1.3.6.1.4.1.2011.2.25.3.40.40.30.234
    perEvtPclsopmax NOTIFICATION-TYPE
    OBJECTS { rptEvtPeriod, rptEvtValue, rptEvtVldty, rptEvtDateTime, rptEvtObjType, rptEvtParaLen, rptEvtPara}
    STATUS current
    DESCRIPTION
    "Trap of PerEvt: perEvtPclsopmax."
    ::= { optixTrapsPER 234 }

--  1.3.6.1.4.1.2011.2.25.3.40.40.30.235
    perEvtPclsopmin NOTIFICATION-TYPE
    OBJECTS { rptEvtPeriod, rptEvtValue, rptEvtVldty, rptEvtDateTime, rptEvtObjType, rptEvtParaLen, rptEvtPara}
    STATUS current
    DESCRIPTION
    "Trap of PerEvt: perEvtPclsopmin."
    ::= { optixTrapsPER 235 }

--  1.3.6.1.4.1.2011.2.25.3.40.40.30.236
    perEvtPclsopcur NOTIFICATION-TYPE
    OBJECTS { rptEvtPeriod, rptEvtValue, rptEvtVldty, rptEvtDateTime, rptEvtObjType, rptEvtParaLen, rptEvtPara}
    STATUS current
    DESCRIPTION
    "Trap of PerEvt: perEvtPclsopcur."
    ::= { optixTrapsPER 236 }

--  1.3.6.1.4.1.2011.2.25.3.40.40.30.237
    perEvtPclssnmax NOTIFICATION-TYPE
    OBJECTS { rptEvtPeriod, rptEvtValue, rptEvtVldty, rptEvtDateTime, rptEvtObjType, rptEvtParaLen, rptEvtPara}
    STATUS current
    DESCRIPTION
    "Trap of PerEvt: perEvtPclssnmax."
    ::= { optixTrapsPER 237 }

--  1.3.6.1.4.1.2011.2.25.3.40.40.30.238
    perEvtPclssnmin NOTIFICATION-TYPE
    OBJECTS { rptEvtPeriod, rptEvtValue, rptEvtVldty, rptEvtDateTime, rptEvtObjType, rptEvtParaLen, rptEvtPara}
    STATUS current
    DESCRIPTION
    "Trap of PerEvt: perEvtPclssnmin."
    ::= { optixTrapsPER 238 }

--  1.3.6.1.4.1.2011.2.25.3.40.40.30.239
    perEvtPclssncur NOTIFICATION-TYPE
    OBJECTS { rptEvtPeriod, rptEvtValue, rptEvtVldty, rptEvtDateTime, rptEvtObjType, rptEvtParaLen, rptEvtPara}
    STATUS current
    DESCRIPTION
    "Trap of PerEvt: perEvtPclssncur."
    ::= { optixTrapsPER 239 }

--  1.3.6.1.4.1.2011.2.25.3.40.40.30.8612
    perEvtOoprlmax NOTIFICATION-TYPE
    OBJECTS { rptEvtPeriod, rptEvtValue, rptEvtVldty, rptEvtDateTime, rptEvtObjType, rptEvtParaLen, rptEvtPara}
    STATUS current
    DESCRIPTION
    "Trap of PerEvt: Output Optical Power Return Loss Maximum."
    ::= { optixTrapsPER 8612 }

--  1.3.6.1.4.1.2011.2.25.3.40.40.30.8613
    perEvtOoprlmin NOTIFICATION-TYPE
    OBJECTS { rptEvtPeriod, rptEvtValue, rptEvtVldty, rptEvtDateTime, rptEvtObjType, rptEvtParaLen, rptEvtPara}
    STATUS current
    DESCRIPTION
    "Trap of PerEvt: Output Optical Power Return Loss Minimum."
    ::= { optixTrapsPER 8613 }

--  1.3.6.1.4.1.2011.2.25.3.40.40.30.8614
    perEvtOoprlcur NOTIFICATION-TYPE
    OBJECTS { rptEvtPeriod, rptEvtValue, rptEvtVldty, rptEvtDateTime, rptEvtObjType, rptEvtParaLen, rptEvtPara}
    STATUS current
    DESCRIPTION
    "Trap of PerEvt: Output Optical Power Return Loss Current."
    ::= { optixTrapsPER 8614 }

--  1.3.6.1.4.1.2011.2.25.3.40.40.30.14976
    perEvtApdtemmax NOTIFICATION-TYPE
    OBJECTS { rptEvtPeriod, rptEvtValue, rptEvtVldty, rptEvtDateTime, rptEvtObjType, rptEvtParaLen, rptEvtPara}
    STATUS current
    DESCRIPTION
    "Trap of PerEvt: perEvtApdtemmax."
    ::= { optixTrapsPER 14976 }

--  1.3.6.1.4.1.2011.2.25.3.40.40.30.14977
    perEvtApdtemmin NOTIFICATION-TYPE
    OBJECTS { rptEvtPeriod, rptEvtValue, rptEvtVldty, rptEvtDateTime, rptEvtObjType, rptEvtParaLen, rptEvtPara}
    STATUS current
    DESCRIPTION
    "Trap of PerEvt: perEvtApdtemmin."
    ::= { optixTrapsPER 14977 }

--  1.3.6.1.4.1.2011.2.25.3.40.40.30.14978
    perEvtApdtemcur NOTIFICATION-TYPE
    OBJECTS { rptEvtPeriod, rptEvtValue, rptEvtVldty, rptEvtDateTime, rptEvtObjType, rptEvtParaLen, rptEvtPara}
    STATUS current
    DESCRIPTION
    "Trap of PerEvt: perEvtApdtemcur."
    ::= { optixTrapsPER 14978 }

--  1.3.6.1.4.1.2011.2.25.3.40.40.30.14994
    perEvtApdcoolmax NOTIFICATION-TYPE
    OBJECTS { rptEvtPeriod, rptEvtValue, rptEvtVldty, rptEvtDateTime, rptEvtObjType, rptEvtParaLen, rptEvtPara}
    STATUS current
    DESCRIPTION
    "Trap of PerEvt: perEvtApdcoolmax."
    ::= { optixTrapsPER 14994 }

--  1.3.6.1.4.1.2011.2.25.3.40.40.30.14995
    perEvtApdcoolmin NOTIFICATION-TYPE
    OBJECTS { rptEvtPeriod, rptEvtValue, rptEvtVldty, rptEvtDateTime, rptEvtObjType, rptEvtParaLen, rptEvtPara}
    STATUS current
    DESCRIPTION
    "Trap of PerEvt: perEvtApdcoolmin."
    ::= { optixTrapsPER 14995 }

--  1.3.6.1.4.1.2011.2.25.3.40.40.30.14996
    perEvtApdcoolcur NOTIFICATION-TYPE
    OBJECTS { rptEvtPeriod, rptEvtValue, rptEvtVldty, rptEvtDateTime, rptEvtObjType, rptEvtParaLen, rptEvtPara}
    STATUS current
    DESCRIPTION
    "Trap of PerEvt: perEvtApdcoolcur."
    ::= { optixTrapsPER 14996 }

--  1.3.6.1.4.1.2011.2.25.3.40.40.30.15476
    perEvtRmiopmax NOTIFICATION-TYPE
    OBJECTS { rptEvtPeriod, rptEvtValue, rptEvtVldty, rptEvtDateTime, rptEvtObjType, rptEvtParaLen, rptEvtPara}
    STATUS current
    DESCRIPTION
    "Trap of PerEvt: Maximum input optical power of the Raman amplifier."
    ::= { optixTrapsPER 15476 }

--  1.3.6.1.4.1.2011.2.25.3.40.40.30.15477
    perEvtRmiopmin NOTIFICATION-TYPE
    OBJECTS { rptEvtPeriod, rptEvtValue, rptEvtVldty, rptEvtDateTime, rptEvtObjType, rptEvtParaLen, rptEvtPara}
    STATUS current
    DESCRIPTION
    "Trap of PerEvt: Minimum input optical power of the Raman amplifier."
    ::= { optixTrapsPER 15477 }

--  1.3.6.1.4.1.2011.2.25.3.40.40.30.15478
    perEvtRmiopcur NOTIFICATION-TYPE
    OBJECTS { rptEvtPeriod, rptEvtValue, rptEvtVldty, rptEvtDateTime, rptEvtObjType, rptEvtParaLen, rptEvtPara}
    STATUS current
    DESCRIPTION
    "Trap of PerEvt: Current input optical power of the Raman amplifier."
    ::= { optixTrapsPER 15478 }

--  1.3.6.1.4.1.2011.2.25.3.40.40.30.15483
    perEvtAswiopmax NOTIFICATION-TYPE
    OBJECTS { rptEvtPeriod, rptEvtValue, rptEvtVldty, rptEvtDateTime, rptEvtObjType, rptEvtParaLen, rptEvtPara}
    STATUS current
    DESCRIPTION
    "Trap of PerEvt: maximun of single wave input power."
    ::= { optixTrapsPER 15483 }

--  1.3.6.1.4.1.2011.2.25.3.40.40.30.15484
    perEvtAswiopmin NOTIFICATION-TYPE
    OBJECTS { rptEvtPeriod, rptEvtValue, rptEvtVldty, rptEvtDateTime, rptEvtObjType, rptEvtParaLen, rptEvtPara}
    STATUS current
    DESCRIPTION
    "Trap of PerEvt: minimum of single wave input power."
    ::= { optixTrapsPER 15484 }

--  1.3.6.1.4.1.2011.2.25.3.40.40.30.15485
    perEvtAswiopcur NOTIFICATION-TYPE
    OBJECTS { rptEvtPeriod, rptEvtValue, rptEvtVldty, rptEvtDateTime, rptEvtObjType, rptEvtParaLen, rptEvtPara}
    STATUS current
    DESCRIPTION
    "Trap of PerEvt: current value of single wave input power."
    ::= { optixTrapsPER 15485 }

--  1.3.6.1.4.1.2011.2.25.3.40.40.30.15486
    perEvtAaospcur NOTIFICATION-TYPE
    OBJECTS { rptEvtPeriod, rptEvtValue, rptEvtVldty, rptEvtDateTime, rptEvtObjType, rptEvtParaLen, rptEvtPara}
    STATUS current
    DESCRIPTION
    "Trap of PerEvt: current value of average output signal power."
    ::= { optixTrapsPER 15486 }

--  1.3.6.1.4.1.2011.2.25.3.40.40.30.15487
    perEvtAswoopmax NOTIFICATION-TYPE
    OBJECTS { rptEvtPeriod, rptEvtValue, rptEvtVldty, rptEvtDateTime, rptEvtObjType, rptEvtParaLen, rptEvtPara}
    STATUS current
    DESCRIPTION
    "Trap of PerEvt: maximum of single wave output power."
    ::= { optixTrapsPER 15487 }

--  1.3.6.1.4.1.2011.2.25.3.40.40.30.15488
    perEvtAswoopmin NOTIFICATION-TYPE
    OBJECTS { rptEvtPeriod, rptEvtValue, rptEvtVldty, rptEvtDateTime, rptEvtObjType, rptEvtParaLen, rptEvtPara}
    STATUS current
    DESCRIPTION
    "Trap of PerEvt: minimum of single wave output power."
    ::= { optixTrapsPER 15488 }

--  1.3.6.1.4.1.2011.2.25.3.40.40.30.15489
    perEvtAswoopcur NOTIFICATION-TYPE
    OBJECTS { rptEvtPeriod, rptEvtValue, rptEvtVldty, rptEvtDateTime, rptEvtObjType, rptEvtParaLen, rptEvtPara}
    STATUS current
    DESCRIPTION
    "Trap of PerEvt: current value of single wave output power."
    ::= { optixTrapsPER 15489 }

--  1.3.6.1.4.1.2011.2.25.3.40.40.30.15490
    perEvtAswsnrmax NOTIFICATION-TYPE
    OBJECTS { rptEvtPeriod, rptEvtValue, rptEvtVldty, rptEvtDateTime, rptEvtObjType, rptEvtParaLen, rptEvtPara}
    STATUS current
    DESCRIPTION
    "Trap of PerEvt: maximum of single wave osnr."
    ::= { optixTrapsPER 15490 }

--  1.3.6.1.4.1.2011.2.25.3.40.40.30.15491
    perEvtAswsnrmin NOTIFICATION-TYPE
    OBJECTS { rptEvtPeriod, rptEvtValue, rptEvtVldty, rptEvtDateTime, rptEvtObjType, rptEvtParaLen, rptEvtPara}
    STATUS current
    DESCRIPTION
    "Trap of PerEvt: minimum of single wave osnr."
    ::= { optixTrapsPER 15491 }

--  1.3.6.1.4.1.2011.2.25.3.40.40.30.15492
    perEvtAswsnrcur NOTIFICATION-TYPE
    OBJECTS { rptEvtPeriod, rptEvtValue, rptEvtVldty, rptEvtDateTime, rptEvtObjType, rptEvtParaLen, rptEvtPara}
    STATUS current
    DESCRIPTION
    "Trap of PerEvt: current value of single wave osnr."
    ::= { optixTrapsPER 15492 }

--  1.3.6.1.4.1.2011.2.25.3.40.40.30.15493
    perEvtAswsnlmax NOTIFICATION-TYPE
    OBJECTS { rptEvtPeriod, rptEvtValue, rptEvtVldty, rptEvtDateTime, rptEvtObjType, rptEvtParaLen, rptEvtPara}
    STATUS current
    DESCRIPTION
    "Trap of PerEvt: maximum of single wave osnr loss."
    ::= { optixTrapsPER 15493 }

--  1.3.6.1.4.1.2011.2.25.3.40.40.30.15494
    perEvtAswsnlmin NOTIFICATION-TYPE
    OBJECTS { rptEvtPeriod, rptEvtValue, rptEvtVldty, rptEvtDateTime, rptEvtObjType, rptEvtParaLen, rptEvtPara}
    STATUS current
    DESCRIPTION
    "Trap of PerEvt: minimum of single wave osnr loss."
    ::= { optixTrapsPER 15494 }

--  1.3.6.1.4.1.2011.2.25.3.40.40.30.15495
    perEvtAswsnlcur NOTIFICATION-TYPE
    OBJECTS { rptEvtPeriod, rptEvtValue, rptEvtVldty, rptEvtDateTime, rptEvtObjType, rptEvtParaLen, rptEvtPara}
    STATUS current
    DESCRIPTION
    "Trap of PerEvt: current value of single wave osnr loss."
    ::= { optixTrapsPER 15495 }

--  1.3.6.1.4.1.2011.2.25.3.40.40.30.15496
    perEvtAainpmax NOTIFICATION-TYPE
    OBJECTS { rptEvtPeriod, rptEvtValue, rptEvtVldty, rptEvtDateTime, rptEvtObjType, rptEvtParaLen, rptEvtPara}
    STATUS current
    DESCRIPTION
    "Trap of PerEvt: maximum of average input noise power."
    ::= { optixTrapsPER 15496 }

--  1.3.6.1.4.1.2011.2.25.3.40.40.30.15497
    perEvtAainpmin NOTIFICATION-TYPE
    OBJECTS { rptEvtPeriod, rptEvtValue, rptEvtVldty, rptEvtDateTime, rptEvtObjType, rptEvtParaLen, rptEvtPara}
    STATUS current
    DESCRIPTION
    "Trap of PerEvt: minimum of average input noise power."
    ::= { optixTrapsPER 15497 }

--  1.3.6.1.4.1.2011.2.25.3.40.40.30.15498
    perEvtAainpcur NOTIFICATION-TYPE
    OBJECTS { rptEvtPeriod, rptEvtValue, rptEvtVldty, rptEvtDateTime, rptEvtObjType, rptEvtParaLen, rptEvtPara}
    STATUS current
    DESCRIPTION
    "Trap of PerEvt: current value of average input noise power."
    ::= { optixTrapsPER 15498 }

--  1.3.6.1.4.1.2011.2.25.3.40.40.30.15499
    perEvtAaispmax NOTIFICATION-TYPE
    OBJECTS { rptEvtPeriod, rptEvtValue, rptEvtVldty, rptEvtDateTime, rptEvtObjType, rptEvtParaLen, rptEvtPara}
    STATUS current
    DESCRIPTION
    "Trap of PerEvt: maximum of average input signal power."
    ::= { optixTrapsPER 15499 }

--  1.3.6.1.4.1.2011.2.25.3.40.40.30.15500
    perEvtAaispmin NOTIFICATION-TYPE
    OBJECTS { rptEvtPeriod, rptEvtValue, rptEvtVldty, rptEvtDateTime, rptEvtObjType, rptEvtParaLen, rptEvtPara}
    STATUS current
    DESCRIPTION
    "Trap of PerEvt: minimum of average input signal power."
    ::= { optixTrapsPER 15500 }

--  1.3.6.1.4.1.2011.2.25.3.40.40.30.15501
    perEvtAaispcur NOTIFICATION-TYPE
    OBJECTS { rptEvtPeriod, rptEvtValue, rptEvtVldty, rptEvtDateTime, rptEvtObjType, rptEvtParaLen, rptEvtPara}
    STATUS current
    DESCRIPTION
    "Trap of PerEvt: current value of average input signal power."
    ::= { optixTrapsPER 15501 }

--  1.3.6.1.4.1.2011.2.25.3.40.40.30.15502
    perEvtAaonpmax NOTIFICATION-TYPE
    OBJECTS { rptEvtPeriod, rptEvtValue, rptEvtVldty, rptEvtDateTime, rptEvtObjType, rptEvtParaLen, rptEvtPara}
    STATUS current
    DESCRIPTION
    "Trap of PerEvt: maximum of average output noise power."
    ::= { optixTrapsPER 15502 }

--  1.3.6.1.4.1.2011.2.25.3.40.40.30.15503
    perEvtAaonpmin NOTIFICATION-TYPE
    OBJECTS { rptEvtPeriod, rptEvtValue, rptEvtVldty, rptEvtDateTime, rptEvtObjType, rptEvtParaLen, rptEvtPara}
    STATUS current
    DESCRIPTION
    "Trap of PerEvt: minimum of average output noise power."
    ::= { optixTrapsPER 15503 }

--  1.3.6.1.4.1.2011.2.25.3.40.40.30.15504
    perEvtAaonpcur NOTIFICATION-TYPE
    OBJECTS { rptEvtPeriod, rptEvtValue, rptEvtVldty, rptEvtDateTime, rptEvtObjType, rptEvtParaLen, rptEvtPara}
    STATUS current
    DESCRIPTION
    "Trap of PerEvt: current value of average output noise power."
    ::= { optixTrapsPER 15504 }

--  1.3.6.1.4.1.2011.2.25.3.40.40.30.15505
    perEvtAaospmax NOTIFICATION-TYPE
    OBJECTS { rptEvtPeriod, rptEvtValue, rptEvtVldty, rptEvtDateTime, rptEvtObjType, rptEvtParaLen, rptEvtPara}
    STATUS current
    DESCRIPTION
    "Trap of PerEvt: maximum of average output signal power."
    ::= { optixTrapsPER 15505 }

--  1.3.6.1.4.1.2011.2.25.3.40.40.30.15506
    perEvtAaospmin NOTIFICATION-TYPE
    OBJECTS { rptEvtPeriod, rptEvtValue, rptEvtVldty, rptEvtDateTime, rptEvtObjType, rptEvtParaLen, rptEvtPara}
    STATUS current
    DESCRIPTION
    "Trap of PerEvt: minimum of average output signal power."
    ::= { optixTrapsPER 15506 }

--  1.3.6.1.4.1.2011.2.25.3.40.40.30.15862
    perEvtPumporpcur NOTIFICATION-TYPE
    OBJECTS { rptEvtPeriod, rptEvtValue, rptEvtVldty, rptEvtDateTime, rptEvtObjType, rptEvtParaLen, rptEvtPara}
    STATUS current
    DESCRIPTION
    "Trap of PerEvt: current optical reflection power."
    ::= { optixTrapsPER 15862 }

--  1.3.6.1.4.1.2011.2.25.3.40.40.30.15863
    perEvtPumporpmax NOTIFICATION-TYPE
    OBJECTS { rptEvtPeriod, rptEvtValue, rptEvtVldty, rptEvtDateTime, rptEvtObjType, rptEvtParaLen, rptEvtPara}
    STATUS current
    DESCRIPTION
    "Trap of PerEvt: maximum optical reflection power."
    ::= { optixTrapsPER 15863 }

--  1.3.6.1.4.1.2011.2.25.3.40.40.30.15864
    perEvtPumporpmin NOTIFICATION-TYPE
    OBJECTS { rptEvtPeriod, rptEvtValue, rptEvtVldty, rptEvtDateTime, rptEvtObjType, rptEvtParaLen, rptEvtPara}
    STATUS current
    DESCRIPTION
    "Trap of PerEvt: minimum optical reflection power."
    ::= { optixTrapsPER 15864 }

--  1.3.6.1.4.1.2011.2.25.3.40.40.30.15877
    perEvtFswsnlmax NOTIFICATION-TYPE
    OBJECTS { rptEvtPeriod, rptEvtValue, rptEvtVldty, rptEvtDateTime, rptEvtObjType, rptEvtParaLen, rptEvtPara}
    STATUS current
    DESCRIPTION
    "Trap of PerEvt: Maximum single-wavelength OSNR degradation amount."
    ::= { optixTrapsPER 15877 }

--  1.3.6.1.4.1.2011.2.25.3.40.40.30.15878
    perEvtFswsnlmin NOTIFICATION-TYPE
    OBJECTS { rptEvtPeriod, rptEvtValue, rptEvtVldty, rptEvtDateTime, rptEvtObjType, rptEvtParaLen, rptEvtPara}
    STATUS current
    DESCRIPTION
    "Trap of PerEvt: Minimum single-wavelength OSNR degradation amount."
    ::= { optixTrapsPER 15878 }

--  1.3.6.1.4.1.2011.2.25.3.40.40.30.15879
    perEvtFswsnlcur NOTIFICATION-TYPE
    OBJECTS { rptEvtPeriod, rptEvtValue, rptEvtVldty, rptEvtDateTime, rptEvtObjType, rptEvtParaLen, rptEvtPara}
    STATUS current
    DESCRIPTION
    "Trap of PerEvt: Current single-wavelength OSNR degradation amount."
    ::= { optixTrapsPER 15879 }

--  1.3.6.1.4.1.2011.2.25.3.40.40.30.15900
    perEvtSubcardtmpmax NOTIFICATION-TYPE
    OBJECTS { rptEvtPeriod, rptEvtValue, rptEvtVldty, rptEvtDateTime, rptEvtObjType, rptEvtParaLen, rptEvtPara}
    STATUS current
    DESCRIPTION
    "Trap of PerEvt: Maximum sub-card temperature."
    ::= { optixTrapsPER 15900 }

--  1.3.6.1.4.1.2011.2.25.3.40.40.30.15901
    perEvtSubcardtmpmin NOTIFICATION-TYPE
    OBJECTS { rptEvtPeriod, rptEvtValue, rptEvtVldty, rptEvtDateTime, rptEvtObjType, rptEvtParaLen, rptEvtPara}
    STATUS current
    DESCRIPTION
    "Trap of PerEvt: Minimum sub-card temperature."
    ::= { optixTrapsPER 15901 }

--  1.3.6.1.4.1.2011.2.25.3.40.40.30.15902
    perEvtSubcardtmpcur NOTIFICATION-TYPE
    OBJECTS { rptEvtPeriod, rptEvtValue, rptEvtVldty, rptEvtDateTime, rptEvtObjType, rptEvtParaLen, rptEvtPara}
    STATUS current
    DESCRIPTION
    "Trap of PerEvt: Current sub-card temperature."
    ::= { optixTrapsPER 15902 }

--  1.3.6.1.4.1.2011.2.25.3.40.40.30.15980
    perEvtGaincur NOTIFICATION-TYPE
    OBJECTS { rptEvtPeriod, rptEvtValue, rptEvtVldty, rptEvtDateTime, rptEvtObjType, rptEvtParaLen, rptEvtPara}
    STATUS current
    DESCRIPTION
    "Trap of PerEvt: Current Gain."
    ::= { optixTrapsPER 15980 }

--  1.3.6.1.4.1.2011.2.25.3.40.40.30.15981
    perEvtGainmax NOTIFICATION-TYPE
    OBJECTS { rptEvtPeriod, rptEvtValue, rptEvtVldty, rptEvtDateTime, rptEvtObjType, rptEvtParaLen, rptEvtPara}
    STATUS current
    DESCRIPTION
    "Trap of PerEvt: Maximum Gain."
    ::= { optixTrapsPER 15981 }

--  1.3.6.1.4.1.2011.2.25.3.40.40.30.15982
    perEvtGainmin NOTIFICATION-TYPE
    OBJECTS { rptEvtPeriod, rptEvtValue, rptEvtVldty, rptEvtDateTime, rptEvtObjType, rptEvtParaLen, rptEvtPara}
    STATUS current
    DESCRIPTION
    "Trap of PerEvt: Minimum Gain."
    ::= { optixTrapsPER 15982 }

--  1.3.6.1.4.1.2011.2.25.3.40.40.30.16135
    perEvtMcsoopmax NOTIFICATION-TYPE
    OBJECTS { rptEvtPeriod, rptEvtValue, rptEvtVldty, rptEvtDateTime, rptEvtObjType, rptEvtParaLen, rptEvtPara}
    STATUS current
    DESCRIPTION
    "Trap of PerEvt: Maximum output optical power of the main channel signal."
    ::= { optixTrapsPER 16135 }

--  1.3.6.1.4.1.2011.2.25.3.40.40.30.16136
    perEvtMcsoopmin NOTIFICATION-TYPE
    OBJECTS { rptEvtPeriod, rptEvtValue, rptEvtVldty, rptEvtDateTime, rptEvtObjType, rptEvtParaLen, rptEvtPara}
    STATUS current
    DESCRIPTION
    "Trap of PerEvt: Minimum output optical power of the main channel signal."
    ::= { optixTrapsPER 16136 }

--  1.3.6.1.4.1.2011.2.25.3.40.40.30.16137
    perEvtMcsoopcur NOTIFICATION-TYPE
    OBJECTS { rptEvtPeriod, rptEvtValue, rptEvtVldty, rptEvtDateTime, rptEvtObjType, rptEvtParaLen, rptEvtPara}
    STATUS current
    DESCRIPTION
    "Trap of PerEvt: Current output optical power of the main channel signal."
    ::= { optixTrapsPER 16137 }

--  1.3.6.1.4.1.2011.2.25.3.40.40.30.16164
    perEvtEvoaattncur NOTIFICATION-TYPE
    OBJECTS { rptEvtPeriod, rptEvtValue, rptEvtVldty, rptEvtDateTime, rptEvtObjType, rptEvtParaLen, rptEvtPara}
    STATUS current
    DESCRIPTION
    "Trap of PerEvt: Current EVOA attenuation."
    ::= { optixTrapsPER 16164 }

--  1.3.6.1.4.1.2011.2.25.3.40.40.30.16165
    perEvtEvoaattnmax NOTIFICATION-TYPE
    OBJECTS { rptEvtPeriod, rptEvtValue, rptEvtVldty, rptEvtDateTime, rptEvtObjType, rptEvtParaLen, rptEvtPara}
    STATUS current
    DESCRIPTION
    "Trap of PerEvt: Maximum EVOA attenuation."
    ::= { optixTrapsPER 16165 }

--  1.3.6.1.4.1.2011.2.25.3.40.40.30.16166
    perEvtEvoaattnmin NOTIFICATION-TYPE
    OBJECTS { rptEvtPeriod, rptEvtValue, rptEvtVldty, rptEvtDateTime, rptEvtObjType, rptEvtParaLen, rptEvtPara}
    STATUS current
    DESCRIPTION
    "Trap of PerEvt: Minimum EVOA attenuation."
    ::= { optixTrapsPER 16166 }



	--  1.3.6.1.4.1.2011.2.25.3.40.40.30.15874
		perEvtFswsnrmax NOTIFICATION-TYPE
		OBJECTS { rptEvtPeriod, rptEvtValue, rptEvtVldty, rptEvtDateTime, rptEvtObjType, rptEvtParaLen, rptEvtPara}
		STATUS current
		DESCRIPTION
		"Trap of PerEvt: Maximum single-wavelength OSNR."
		::= { optixTrapsPER 15874 }

    --  1.3.6.1.4.1.2011.2.25.3.40.40.30.15875
		perEvtFswsnrmin NOTIFICATION-TYPE
		OBJECTS { rptEvtPeriod, rptEvtValue, rptEvtVldty, rptEvtDateTime, rptEvtObjType, rptEvtParaLen, rptEvtPara}
		STATUS current
		DESCRIPTION
		"Trap of PerEvt: Minimum single-wavelength OSNR."
		::= { optixTrapsPER 15875 }

    --  1.3.6.1.4.1.2011.2.25.3.40.40.30.15876
		perEvtFswsnrcur NOTIFICATION-TYPE
		OBJECTS { rptEvtPeriod, rptEvtValue, rptEvtVldty, rptEvtDateTime, rptEvtObjType, rptEvtParaLen, rptEvtPara}
		STATUS current
		DESCRIPTION
		"Trap of PerEvt: Current single-wavelength OSNR."
		::= { optixTrapsPER 15876 }

	--  1.3.6.1.4.1.2011.2.25.3.40.40.30.16097
    perEvtSopcur NOTIFICATION-TYPE
    OBJECTS { rptEvtPeriod, rptEvtValue, rptEvtVldty, rptEvtDateTime, rptEvtObjType, rptEvtParaLen, rptEvtPara}
    STATUS current
    DESCRIPTION
    "Trap of PerEvt: Current State of Polarization."
    ::= { optixTrapsPER 16097 }

--  1.3.6.1.4.1.2011.2.25.3.40.40.30.16098
    perEvtSopmin NOTIFICATION-TYPE
    OBJECTS { rptEvtPeriod, rptEvtValue, rptEvtVldty, rptEvtDateTime, rptEvtObjType, rptEvtParaLen, rptEvtPara}
    STATUS current
    DESCRIPTION
    "Trap of PerEvt: Minimum State of Polarization."
    ::= { optixTrapsPER 16098 }

--  1.3.6.1.4.1.2011.2.25.3.40.40.30.16099
    perEvtSopmax NOTIFICATION-TYPE
    OBJECTS { rptEvtPeriod, rptEvtValue, rptEvtVldty, rptEvtDateTime, rptEvtObjType, rptEvtParaLen, rptEvtPara}
    STATUS current
    DESCRIPTION
    "Trap of PerEvt: Maximum State of Polarization."
    ::= { optixTrapsPER 16099 }

    --  1.3.6.1.4.1.2011.2.25.3.40.40.30.134
       perEvtfecCorrected1BitCount NOTIFICATION-TYPE
       OBJECTS { rptEvtPeriod, rptEvtValue, rptEvtVldty, rptEvtDateTime, rptEvtObjType, rptEvtParaLen, rptEvtPara}
       STATUS current
       DESCRIPTION
       "Trap of PerEvt: Forward Error Correction - Corrected 1 Bit Count"
       ::= { optixTrapsPER  134}

    --  1.3.6.1.4.1.2011.2.25.3.40.40.30.135
       perEvtfecCorrectedByteCount NOTIFICATION-TYPE
       OBJECTS { rptEvtPeriod, rptEvtValue, rptEvtVldty, rptEvtDateTime, rptEvtObjType, rptEvtParaLen, rptEvtPara}
       STATUS current
       DESCRIPTION
       "Trap of PerEvt: Forward Error Correction - Corrected Byte Count"
       ::= { optixTrapsPER  135}

    --  1.3.6.1.4.1.2011.2.25.3.40.40.30.136
       perEvtfecUnCorrectedBlockCount NOTIFICATION-TYPE
       OBJECTS { rptEvtPeriod, rptEvtValue, rptEvtVldty, rptEvtDateTime, rptEvtObjType, rptEvtParaLen, rptEvtPara}
       STATUS current
       DESCRIPTION
       "Trap of PerEvt: Forward Error Correction - UnCorrected Block Count"
       ::= { optixTrapsPER  136}
    --  1.3.6.1.4.1.2011.2.25.3.40.40.30.188
       perEvtxcstmpmax NOTIFICATION-TYPE
       OBJECTS { rptEvtPeriod, rptEvtValue, rptEvtVldty, rptEvtDateTime, rptEvtObjType, rptEvtParaLen, rptEvtPara}
       STATUS current
       DESCRIPTION
       "Trap of PerEvt: Board Temperature Maximum"
       ::= { optixTrapsPER  188}

    --  1.3.6.1.4.1.2011.2.25.3.40.40.30.189
       perEvtxcstmpmin NOTIFICATION-TYPE
       OBJECTS { rptEvtPeriod, rptEvtValue, rptEvtVldty, rptEvtDateTime, rptEvtObjType, rptEvtParaLen, rptEvtPara}
       STATUS current
       DESCRIPTION
       "Trap of PerEvt: Board Temperature Minimum"
       ::= { optixTrapsPER  189}

    --  1.3.6.1.4.1.2011.2.25.3.40.40.30.190
       perEvtxcstmpcur NOTIFICATION-TYPE
       OBJECTS { rptEvtPeriod, rptEvtValue, rptEvtVldty, rptEvtDateTime, rptEvtObjType, rptEvtParaLen, rptEvtPara}
       STATUS current
       DESCRIPTION
       "Trap of PerEvt: Board Temperature Cur-Value"
       ::= { optixTrapsPER  190}

    --  1.3.6.1.4.1.2011.2.25.3.40.40.30.198
       perEvtlsoopmax NOTIFICATION-TYPE
       OBJECTS { rptEvtPeriod, rptEvtValue, rptEvtVldty, rptEvtDateTime, rptEvtObjType, rptEvtParaLen, rptEvtPara}
       STATUS current
       DESCRIPTION
       "Trap of PerEvt: Laser Output Of Power Maximum"
       ::= { optixTrapsPER  198}

     --  1.3.6.1.4.1.2011.2.25.3.40.40.30.15626
       perEvtEthEsr NOTIFICATION-TYPE
       OBJECTS { rptEvtPeriod, rptEvtValue, rptEvtVldty, rptEvtDateTime, rptEvtObjType, rptEvtParaLen, rptEvtPara}
       STATUS current
       DESCRIPTION
       "Trap of PerEvt: 40GE/100GE Ratio of Errored Second"
       ::= { optixTrapsPER  15626}

    --  1.3.6.1.4.1.2011.2.25.3.40.40.30.199
       perEvtlsoopmin NOTIFICATION-TYPE
       OBJECTS { rptEvtPeriod, rptEvtValue, rptEvtVldty, rptEvtDateTime, rptEvtObjType, rptEvtParaLen, rptEvtPara}
       STATUS current
       DESCRIPTION
       "Trap of PerEvt: Laser Output Of Power Minimum"
       ::= { optixTrapsPER  199}

    --  1.3.6.1.4.1.2011.2.25.3.40.40.30.200
       perEvtlsoopcur NOTIFICATION-TYPE
       OBJECTS { rptEvtPeriod, rptEvtValue, rptEvtVldty, rptEvtDateTime, rptEvtObjType, rptEvtParaLen, rptEvtPara}
       STATUS current
       DESCRIPTION
       "Trap of PerEvt: Laser Output Of Power Cur-Value"
       ::= { optixTrapsPER  200}

    --  1.3.6.1.4.1.2011.2.25.3.40.40.30.201
       perEvtlsiopmax NOTIFICATION-TYPE
       OBJECTS { rptEvtPeriod, rptEvtValue, rptEvtVldty, rptEvtDateTime, rptEvtObjType, rptEvtParaLen, rptEvtPara}
       STATUS current
       DESCRIPTION
       "Trap of PerEvt: Laser Input Of Power Maximum"
       ::= { optixTrapsPER  201}

    --  1.3.6.1.4.1.2011.2.25.3.40.40.30.202
       perEvtlsiopmin NOTIFICATION-TYPE
       OBJECTS { rptEvtPeriod, rptEvtValue, rptEvtVldty, rptEvtDateTime, rptEvtObjType, rptEvtParaLen, rptEvtPara}
       STATUS current
       DESCRIPTION
       "Trap of PerEvt: Laser Input Of Power Minimum"
       ::= { optixTrapsPER  202}

    --  1.3.6.1.4.1.2011.2.25.3.40.40.30.203
       perEvtlsiopcur NOTIFICATION-TYPE
       OBJECTS { rptEvtPeriod, rptEvtValue, rptEvtVldty, rptEvtDateTime, rptEvtObjType, rptEvtParaLen, rptEvtPara}
       STATUS current
       DESCRIPTION
       "Trap of PerEvt: Laser Input Of Power Cur-Value"
       ::= { optixTrapsPER  203}

    --  1.3.6.1.4.1.2011.2.25.3.40.40.30.204
       perEvtw32LaserWorkingTemperatureMaximum NOTIFICATION-TYPE
       OBJECTS { rptEvtPeriod, rptEvtValue, rptEvtVldty, rptEvtDateTime, rptEvtObjType, rptEvtParaLen, rptEvtPara}
       STATUS current
       DESCRIPTION
       "Trap of PerEvt: Laser Working Temperature Maximum"
       ::= { optixTrapsPER  204}

    --  1.3.6.1.4.1.2011.2.25.3.40.40.30.205
       perEvtw32LaserWorkingTemperatureMinimum NOTIFICATION-TYPE
       OBJECTS { rptEvtPeriod, rptEvtValue, rptEvtVldty, rptEvtDateTime, rptEvtObjType, rptEvtParaLen, rptEvtPara}
       STATUS current
       DESCRIPTION
       "Trap of PerEvt: Laser Working Temperature Minimum"
       ::= { optixTrapsPER  205}

    --  1.3.6.1.4.1.2011.2.25.3.40.40.30.206
       perEvtw32LaserWorkingTemperatureCurrent NOTIFICATION-TYPE
       OBJECTS { rptEvtPeriod, rptEvtValue, rptEvtVldty, rptEvtDateTime, rptEvtObjType, rptEvtParaLen, rptEvtPara}
       STATUS current
       DESCRIPTION
       "Trap of PerEvt: Laser Working Temperature Cur-Value"
       ::= { optixTrapsPER  206}

    --  1.3.6.1.4.1.2011.2.25.3.40.40.30.207
       perEvtw32LaserBiasMaximum NOTIFICATION-TYPE
       OBJECTS { rptEvtPeriod, rptEvtValue, rptEvtVldty, rptEvtDateTime, rptEvtObjType, rptEvtParaLen, rptEvtPara}
       STATUS current
       DESCRIPTION
       "Trap of PerEvt: Laser bias Current Maximum"
       ::= { optixTrapsPER  207}

    --  1.3.6.1.4.1.2011.2.25.3.40.40.30.208
       perEvtw32LaserBiasMinimum NOTIFICATION-TYPE
       OBJECTS { rptEvtPeriod, rptEvtValue, rptEvtVldty, rptEvtDateTime, rptEvtObjType, rptEvtParaLen, rptEvtPara}
       STATUS current
       DESCRIPTION
       "Trap of PerEvt: Laser bias Current Minimum"
       ::= { optixTrapsPER  208}

    --  1.3.6.1.4.1.2011.2.25.3.40.40.30.209
       perEvtw32LaserBiasCurrent NOTIFICATION-TYPE
       OBJECTS { rptEvtPeriod, rptEvtValue, rptEvtVldty, rptEvtDateTime, rptEvtObjType, rptEvtParaLen, rptEvtPara}
       STATUS current
       DESCRIPTION
       "Trap of PerEvt: Laser bias Current Cur-Value"
       ::= { optixTrapsPER  209}

    --  1.3.6.1.4.1.2011.2.25.3.40.40.30.210
       perEvtw32SumLaserInputOfPowerMaximum NOTIFICATION-TYPE
       OBJECTS { rptEvtPeriod, rptEvtValue, rptEvtVldty, rptEvtDateTime, rptEvtObjType, rptEvtParaLen, rptEvtPara}
       STATUS current
       DESCRIPTION
       "Trap of PerEvt: Sum Laser Input Of Power Maximum"
       ::= { optixTrapsPER  210}

    --  1.3.6.1.4.1.2011.2.25.3.40.40.30.211
       perEvtw32SumLaserInputOfPowerMinimum NOTIFICATION-TYPE
       OBJECTS { rptEvtPeriod, rptEvtValue, rptEvtVldty, rptEvtDateTime, rptEvtObjType, rptEvtParaLen, rptEvtPara}
       STATUS current
       DESCRIPTION
       "Trap of PerEvt: Sum Laser Input Of Power Minimum"
       ::= { optixTrapsPER  211}

    --  1.3.6.1.4.1.2011.2.25.3.40.40.30.212
       perEvtw32SumLaserInputOfPowerCurrent NOTIFICATION-TYPE
       OBJECTS { rptEvtPeriod, rptEvtValue, rptEvtVldty, rptEvtDateTime, rptEvtObjType, rptEvtParaLen, rptEvtPara}
       STATUS current
       DESCRIPTION
       "Trap of PerEvt: Sum Laser Input Of Power Cur-Value"
       ::= { optixTrapsPER  212}
    --  1.3.6.1.4.1.2011.2.25.3.40.40.30.225
       perEvtlsclcmax NOTIFICATION-TYPE
       OBJECTS { rptEvtPeriod, rptEvtValue, rptEvtVldty, rptEvtDateTime, rptEvtObjType, rptEvtParaLen, rptEvtPara}
       STATUS current
       DESCRIPTION
       "Trap of PerEvt: Laser Cooling Current Maximum"
       ::= { optixTrapsPER  225}

    --  1.3.6.1.4.1.2011.2.25.3.40.40.30.226
       perEvtlsclcmin NOTIFICATION-TYPE
       OBJECTS { rptEvtPeriod, rptEvtValue, rptEvtVldty, rptEvtDateTime, rptEvtObjType, rptEvtParaLen, rptEvtPara}
       STATUS current
       DESCRIPTION
       "Trap of PerEvt: Laser Cooling Current Minimum"
       ::= { optixTrapsPER  226}

    --  1.3.6.1.4.1.2011.2.25.3.40.40.30.227
       perEvtlsclccur NOTIFICATION-TYPE
       OBJECTS { rptEvtPeriod, rptEvtValue, rptEvtVldty, rptEvtDateTime, rptEvtObjType, rptEvtParaLen, rptEvtPara}
       STATUS current
       DESCRIPTION
       "Trap of PerEvt: Laser Cooling Current Cur-Value"
       ::= { optixTrapsPER  227}
    --  1.3.6.1.4.1.2011.2.25.3.40.40.30.252
       perEvtbeforeFECCorrectErrorRatio NOTIFICATION-TYPE
       OBJECTS { rptEvtPeriod, rptEvtValue, rptEvtVldty, rptEvtDateTime, rptEvtObjType, rptEvtParaLen, rptEvtPara}
       STATUS current
       DESCRIPTION
       "Trap of PerEvt: Before FEC Correct Error Ratio"
       ::= { optixTrapsPER  252}

    --  1.3.6.1.4.1.2011.2.25.3.40.40.30.253
       perEvtafterFECCorrectErrorRatio NOTIFICATION-TYPE
       OBJECTS { rptEvtPeriod, rptEvtValue, rptEvtVldty, rptEvtDateTime, rptEvtObjType, rptEvtParaLen, rptEvtPara}
       STATUS current
       DESCRIPTION
       "Trap of PerEvt: After FEC Correct Error Ratio"
       ::= { optixTrapsPER  253}
    --  1.3.6.1.4.1.2011.2.25.3.40.40.30.14416
       perEvtodu2pmbbe NOTIFICATION-TYPE
       OBJECTS { rptEvtPeriod, rptEvtValue, rptEvtVldty, rptEvtDateTime, rptEvtObjType, rptEvtParaLen, rptEvtPara}
       STATUS current
       DESCRIPTION
       "Trap of PerEvt: ODU2 PM Background Block Error"
       ::= { optixTrapsPER  14416}

    --  1.3.6.1.4.1.2011.2.25.3.40.40.30.14417
       perEvtodu2pmes NOTIFICATION-TYPE
       OBJECTS { rptEvtPeriod, rptEvtValue, rptEvtVldty, rptEvtDateTime, rptEvtObjType, rptEvtParaLen, rptEvtPara}
       STATUS current
       DESCRIPTION
       "Trap of PerEvt: ODU2 PM Errored Second"
       ::= { optixTrapsPER  14417}

    --  1.3.6.1.4.1.2011.2.25.3.40.40.30.14418
       perEvtodu2pmses NOTIFICATION-TYPE
       OBJECTS { rptEvtPeriod, rptEvtValue, rptEvtVldty, rptEvtDateTime, rptEvtObjType, rptEvtParaLen, rptEvtPara}
       STATUS current
       DESCRIPTION
       "Trap of PerEvt: ODU2 PM Severely Errored Second"
       ::= { optixTrapsPER  14418}

    --  1.3.6.1.4.1.2011.2.25.3.40.40.30.14419
       perEvtodu2pmuas NOTIFICATION-TYPE
       OBJECTS { rptEvtPeriod, rptEvtValue, rptEvtVldty, rptEvtDateTime, rptEvtObjType, rptEvtParaLen, rptEvtPara}
       STATUS current
       DESCRIPTION
       "Trap of PerEvt: ODU2 PM Unavailable Seconds"
       ::= { optixTrapsPER  14419}

    --  1.3.6.1.4.1.2011.2.25.3.40.40.30.14420
       perEvtodu2pmsesr NOTIFICATION-TYPE
       OBJECTS { rptEvtPeriod, rptEvtValue, rptEvtVldty, rptEvtDateTime, rptEvtObjType, rptEvtParaLen, rptEvtPara}
       STATUS current
       DESCRIPTION
       "Trap of PerEvt: ODU2 PM Severely Errored Second Ratio"
       ::= { optixTrapsPER  14420}

    --  1.3.6.1.4.1.2011.2.25.3.40.40.30.14421
       perEvtodu2pmbber NOTIFICATION-TYPE
       OBJECTS { rptEvtPeriod, rptEvtValue, rptEvtVldty, rptEvtDateTime, rptEvtObjType, rptEvtParaLen, rptEvtPara}
       STATUS current
       DESCRIPTION
       "Trap of PerEvt: ODU2 PM Background Block Error Ratio"
       ::= { optixTrapsPER  14421}

    --  1.3.6.1.4.1.2011.2.25.3.40.40.30.14422
       perEvtodu2pmfebbe NOTIFICATION-TYPE
       OBJECTS { rptEvtPeriod, rptEvtValue, rptEvtVldty, rptEvtDateTime, rptEvtObjType, rptEvtParaLen, rptEvtPara}
       STATUS current
       DESCRIPTION
       "Trap of PerEvt: ODU2 PM Far Background Block Error"
       ::= { optixTrapsPER  14422}

    --  1.3.6.1.4.1.2011.2.25.3.40.40.30.14423
       perEvtodu2pmfees NOTIFICATION-TYPE
       OBJECTS { rptEvtPeriod, rptEvtValue, rptEvtVldty, rptEvtDateTime, rptEvtObjType, rptEvtParaLen, rptEvtPara}
       STATUS current
       DESCRIPTION
       "Trap of PerEvt: ODU2 PM Far Errored Second"
       ::= { optixTrapsPER  14423}

    --  1.3.6.1.4.1.2011.2.25.3.40.40.30.14424
       perEvtodu2pmfeses NOTIFICATION-TYPE
       OBJECTS { rptEvtPeriod, rptEvtValue, rptEvtVldty, rptEvtDateTime, rptEvtObjType, rptEvtParaLen, rptEvtPara}
       STATUS current
       DESCRIPTION
       "Trap of PerEvt: ODU2 PM Far Severely Errored Second"
       ::= { optixTrapsPER  14424}

    --  1.3.6.1.4.1.2011.2.25.3.40.40.30.14425
       perEvtodu2pmfeuas NOTIFICATION-TYPE
       OBJECTS { rptEvtPeriod, rptEvtValue, rptEvtVldty, rptEvtDateTime, rptEvtObjType, rptEvtParaLen, rptEvtPara}
       STATUS current
       DESCRIPTION
       "Trap of PerEvt: ODU2 PM Far Unavailable Seconds"
       ::= { optixTrapsPER  14425}

    --  1.3.6.1.4.1.2011.2.25.3.40.40.30.14426
       perEvtodu2pmfesesr NOTIFICATION-TYPE
       OBJECTS { rptEvtPeriod, rptEvtValue, rptEvtVldty, rptEvtDateTime, rptEvtObjType, rptEvtParaLen, rptEvtPara}
       STATUS current
       DESCRIPTION
       "Trap of PerEvt: ODU2 PM Far Severely Errored Second Ratio"
       ::= { optixTrapsPER  14426}

    --  1.3.6.1.4.1.2011.2.25.3.40.40.30.14427
       perEvtodu2pmfebber NOTIFICATION-TYPE
       OBJECTS { rptEvtPeriod, rptEvtValue, rptEvtVldty, rptEvtDateTime, rptEvtObjType, rptEvtParaLen, rptEvtPara}
       STATUS current
       DESCRIPTION
       "Trap of PerEvt: ODU2 PM Far Background Block Error Ratio"
       ::= { optixTrapsPER  14427}

    --  1.3.6.1.4.1.2011.2.25.3.40.40.30.14428
       perEvtodu3pmbbe NOTIFICATION-TYPE
       OBJECTS { rptEvtPeriod, rptEvtValue, rptEvtVldty, rptEvtDateTime, rptEvtObjType, rptEvtParaLen, rptEvtPara}
       STATUS current
       DESCRIPTION
       "Trap of PerEvt: ODU3 PM Background Block Error"
       ::= { optixTrapsPER  14428}

    --  1.3.6.1.4.1.2011.2.25.3.40.40.30.14429
       perEvtodu3pmes NOTIFICATION-TYPE
       OBJECTS { rptEvtPeriod, rptEvtValue, rptEvtVldty, rptEvtDateTime, rptEvtObjType, rptEvtParaLen, rptEvtPara}
       STATUS current
       DESCRIPTION
       "Trap of PerEvt: ODU3 PM Errored Second"
       ::= { optixTrapsPER  14429}

    --  1.3.6.1.4.1.2011.2.25.3.40.40.30.14430
       perEvtodu3pmses NOTIFICATION-TYPE
       OBJECTS { rptEvtPeriod, rptEvtValue, rptEvtVldty, rptEvtDateTime, rptEvtObjType, rptEvtParaLen, rptEvtPara}
       STATUS current
       DESCRIPTION
       "Trap of PerEvt: ODU3 PM Severely Errored Second"
       ::= { optixTrapsPER  14430}

    --  1.3.6.1.4.1.2011.2.25.3.40.40.30.14431
       perEvtodu3pmuas NOTIFICATION-TYPE
       OBJECTS { rptEvtPeriod, rptEvtValue, rptEvtVldty, rptEvtDateTime, rptEvtObjType, rptEvtParaLen, rptEvtPara}
       STATUS current
       DESCRIPTION
       "Trap of PerEvt: ODU3 PM Unavailable Seconds"
       ::= { optixTrapsPER  14431}

    --  1.3.6.1.4.1.2011.2.25.3.40.40.30.14432
       perEvtodu3pmsesr NOTIFICATION-TYPE
       OBJECTS { rptEvtPeriod, rptEvtValue, rptEvtVldty, rptEvtDateTime, rptEvtObjType, rptEvtParaLen, rptEvtPara}
       STATUS current
       DESCRIPTION
       "Trap of PerEvt: ODU3 PM Severely Errored Second Ratio"
       ::= { optixTrapsPER  14432}

    --  1.3.6.1.4.1.2011.2.25.3.40.40.30.14433
       perEvtodu3pmbber NOTIFICATION-TYPE
       OBJECTS { rptEvtPeriod, rptEvtValue, rptEvtVldty, rptEvtDateTime, rptEvtObjType, rptEvtParaLen, rptEvtPara}
       STATUS current
       DESCRIPTION
       "Trap of PerEvt: ODU3 PM Background Block Error Ratio"
       ::= { optixTrapsPER  14433}

    --  1.3.6.1.4.1.2011.2.25.3.40.40.30.14434
       perEvtodu3pmfebbe NOTIFICATION-TYPE
       OBJECTS { rptEvtPeriod, rptEvtValue, rptEvtVldty, rptEvtDateTime, rptEvtObjType, rptEvtParaLen, rptEvtPara}
       STATUS current
       DESCRIPTION
       "Trap of PerEvt: ODU3 PM Far Background Block Error"
       ::= { optixTrapsPER  14434}

    --  1.3.6.1.4.1.2011.2.25.3.40.40.30.14435
       perEvtodu3pmfees NOTIFICATION-TYPE
       OBJECTS { rptEvtPeriod, rptEvtValue, rptEvtVldty, rptEvtDateTime, rptEvtObjType, rptEvtParaLen, rptEvtPara}
       STATUS current
       DESCRIPTION
       "Trap of PerEvt: ODU3 PM Far Errored Second"
       ::= { optixTrapsPER  14435}

    --  1.3.6.1.4.1.2011.2.25.3.40.40.30.14436
       perEvtodu3pmfeses NOTIFICATION-TYPE
       OBJECTS { rptEvtPeriod, rptEvtValue, rptEvtVldty, rptEvtDateTime, rptEvtObjType, rptEvtParaLen, rptEvtPara}
       STATUS current
       DESCRIPTION
       "Trap of PerEvt: ODU3 PM Far Severely Errored Second"
       ::= { optixTrapsPER  14436}

    --  1.3.6.1.4.1.2011.2.25.3.40.40.30.14437
       perEvtodu3pmfeuas NOTIFICATION-TYPE
       OBJECTS { rptEvtPeriod, rptEvtValue, rptEvtVldty, rptEvtDateTime, rptEvtObjType, rptEvtParaLen, rptEvtPara}
       STATUS current
       DESCRIPTION
       "Trap of PerEvt: ODU3 PM Far Unavailable Seconds"
       ::= { optixTrapsPER  14437}

    --  1.3.6.1.4.1.2011.2.25.3.40.40.30.14438
       perEvtodu3pmfesesr NOTIFICATION-TYPE
       OBJECTS { rptEvtPeriod, rptEvtValue, rptEvtVldty, rptEvtDateTime, rptEvtObjType, rptEvtParaLen, rptEvtPara}
       STATUS current
       DESCRIPTION
       "Trap of PerEvt: ODU3 PM Far Severely Errored Second Ratio"
       ::= { optixTrapsPER  14438}

    --  1.3.6.1.4.1.2011.2.25.3.40.40.30.14439
       perEvtodu3pmfebber NOTIFICATION-TYPE
       OBJECTS { rptEvtPeriod, rptEvtValue, rptEvtVldty, rptEvtDateTime, rptEvtObjType, rptEvtParaLen, rptEvtPara}
       STATUS current
       DESCRIPTION
       "Trap of PerEvt: ODU3 PM Far Background Block Error Ratio"
       ::= { optixTrapsPER  14439}
    --  1.3.6.1.4.1.2011.2.25.3.40.40.30.14902
       perEvtTheDispersionCompensationMaximumValue NOTIFICATION-TYPE
       OBJECTS { rptEvtPeriod, rptEvtValue, rptEvtVldty, rptEvtDateTime, rptEvtObjType, rptEvtParaLen, rptEvtPara}
       STATUS current
       DESCRIPTION
       "Trap of PerEvt: The Dispersion Compensation Maximum Value"
       ::= { optixTrapsPER  14902}

    --  1.3.6.1.4.1.2011.2.25.3.40.40.30.14903
       perEvtTheDispersionCompensationMinimumValue NOTIFICATION-TYPE
       OBJECTS { rptEvtPeriod, rptEvtValue, rptEvtVldty, rptEvtDateTime, rptEvtObjType, rptEvtParaLen, rptEvtPara}
       STATUS current
       DESCRIPTION
       "Trap of PerEvt: The Dispersion Compensation Minimum Value"
       ::= { optixTrapsPER  14903}

    --  1.3.6.1.4.1.2011.2.25.3.40.40.30.14904
       perEvtTheDispersionCompensationCurrentValue NOTIFICATION-TYPE
       OBJECTS { rptEvtPeriod, rptEvtValue, rptEvtVldty, rptEvtDateTime, rptEvtObjType, rptEvtParaLen, rptEvtPara}
       STATUS current
       DESCRIPTION
       "Trap of PerEvt: The Dispersion Compensation Current Value"
       ::= { optixTrapsPER  14904}
--  1.3.6.1.4.1.2011.2.25.3.40.40.30.15009
    perEvtfecbefcorerfloat NOTIFICATION-TYPE
    OBJECTS { rptEvtPeriod, rptEvtValue, rptEvtVldty, rptEvtDateTime, rptEvtObjType, rptEvtParaLen, rptEvtPara}
    STATUS current
    DESCRIPTION
        "Trap of PerEvt: Before FEC Correct Error Ratio"
    ::= { optixTrapsPER  15009}


--  1.3.6.1.4.1.2011.2.25.3.40.40.30.15010
    perEvtfecaftcorerfloat NOTIFICATION-TYPE
    OBJECTS { rptEvtPeriod, rptEvtValue, rptEvtVldty, rptEvtDateTime, rptEvtObjType, rptEvtParaLen, rptEvtPara}
    STATUS current
    DESCRIPTION
        "Trap of PerEvt: After FEC Correct Error Ratio"
    ::= { optixTrapsPER  15010}
--  1.3.6.1.4.1.2011.2.25.3.40.40.30.14926
    perEvtfecaftcoreravr NOTIFICATION-TYPE
    OBJECTS { rptEvtPeriod, rptEvtValue, rptEvtVldty, rptEvtDateTime, rptEvtObjType, rptEvtParaLen, rptEvtPara}
    STATUS current
    DESCRIPTION
        "Trap of PerEvt: Before FEC Correct Error Ratio"
    ::= { optixTrapsPER  14926}


--  1.3.6.1.4.1.2011.2.25.3.40.40.30.14927
    perEvtfecbefcoreravr  NOTIFICATION-TYPE
    OBJECTS { rptEvtPeriod, rptEvtValue, rptEvtVldty, rptEvtDateTime, rptEvtObjType, rptEvtParaLen, rptEvtPara}
    STATUS current
    DESCRIPTION
        "Trap of PerEvt: After FEC Correct Error Ratio"
    ::= { optixTrapsPER  14927}
--  1.3.6.1.4.1.2011.2.25.3.40.40.30.15109
    perEvtOtu4Iaes NOTIFICATION-TYPE
    OBJECTS { rptEvtPeriod, rptEvtValue, rptEvtVldty, rptEvtDateTime, rptEvtObjType, rptEvtParaLen, rptEvtPara}
    STATUS current
    DESCRIPTION
        "Trap of PerEvt: OTU4 SM Incoming Alignment Errored Second"
    ::= { optixTrapsPER  15109}

--  1.3.6.1.4.1.2011.2.25.3.40.40.30.15110
    perEvtOtu4Biaes NOTIFICATION-TYPE
    OBJECTS { rptEvtPeriod, rptEvtValue, rptEvtVldty, rptEvtDateTime, rptEvtObjType, rptEvtParaLen, rptEvtPara}
    STATUS current
    DESCRIPTION
        "Trap of PerEvt: OTU4 SM Backward Incoming Alignment Errored Second"
    ::= { optixTrapsPER  15110}

--  1.3.6.1.4.1.2011.2.25.3.40.40.30.15111
    perEvtOtu4Bbe NOTIFICATION-TYPE
    OBJECTS { rptEvtPeriod, rptEvtValue, rptEvtVldty, rptEvtDateTime, rptEvtObjType, rptEvtParaLen, rptEvtPara}
    STATUS current
    DESCRIPTION
        "Trap of PerEvt: OTU4 SM Background Block Error"
    ::= { optixTrapsPER  15111}

--  1.3.6.1.4.1.2011.2.25.3.40.40.30.15112
    perEvtOtu4Es NOTIFICATION-TYPE
    OBJECTS { rptEvtPeriod, rptEvtValue, rptEvtVldty, rptEvtDateTime, rptEvtObjType, rptEvtParaLen, rptEvtPara}
    STATUS current
    DESCRIPTION
        "Trap of PerEvt: OTU4 SM Errored Second"
    ::= { optixTrapsPER  15112}

--  1.3.6.1.4.1.2011.2.25.3.40.40.30.15113
    perEvtOtu4Ses NOTIFICATION-TYPE
    OBJECTS { rptEvtPeriod, rptEvtValue, rptEvtVldty, rptEvtDateTime, rptEvtObjType, rptEvtParaLen, rptEvtPara}
    STATUS current
    DESCRIPTION
        "Trap of PerEvt: OTU4 SM Severely Errored Second"
    ::= { optixTrapsPER  15113}

--  1.3.6.1.4.1.2011.2.25.3.40.40.30.15114
    perEvtOtu4Uas NOTIFICATION-TYPE
    OBJECTS { rptEvtPeriod, rptEvtValue, rptEvtVldty, rptEvtDateTime, rptEvtObjType, rptEvtParaLen, rptEvtPara}
    STATUS current
    DESCRIPTION
        "Trap of PerEvt: OTU4 SM Unavailable Seconds"
    ::= { optixTrapsPER  15114}

--  1.3.6.1.4.1.2011.2.25.3.40.40.30.15115
    perEvtOtu4Sesr NOTIFICATION-TYPE
    OBJECTS { rptEvtPeriod, rptEvtValue, rptEvtVldty, rptEvtDateTime, rptEvtObjType, rptEvtParaLen, rptEvtPara}
    STATUS current
    DESCRIPTION
        "Trap of PerEvt: OTU4 SM Background Block Error Ratio"
    ::= { optixTrapsPER  15115}

--  1.3.6.1.4.1.2011.2.25.3.40.40.30.15116
    perEvtOtu4Bber NOTIFICATION-TYPE
    OBJECTS { rptEvtPeriod, rptEvtValue, rptEvtVldty, rptEvtDateTime, rptEvtObjType, rptEvtParaLen, rptEvtPara}
    STATUS current
    DESCRIPTION
        "Trap of PerEvt: OTU4 SM Far Background Block Error"
    ::= { optixTrapsPER  15116}

--  1.3.6.1.4.1.2011.2.25.3.40.40.30.15117
    perEvtOtu4Febbe NOTIFICATION-TYPE
    OBJECTS { rptEvtPeriod, rptEvtValue, rptEvtVldty, rptEvtDateTime, rptEvtObjType, rptEvtParaLen, rptEvtPara}
    STATUS current
    DESCRIPTION
        "Trap of PerEvt: OTU4 SM Background Block Error Ratio"
    ::= { optixTrapsPER  15117}

--  1.3.6.1.4.1.2011.2.25.3.40.40.30.15118
    perEvtOtu4Fees NOTIFICATION-TYPE
    OBJECTS { rptEvtPeriod, rptEvtValue, rptEvtVldty, rptEvtDateTime, rptEvtObjType, rptEvtParaLen, rptEvtPara}
    STATUS current
    DESCRIPTION
        "Trap of PerEvt: OTU4 SM Far Errored Second"
    ::= { optixTrapsPER  15118}

--  1.3.6.1.4.1.2011.2.25.3.40.40.30.15119
    perEvtOtu4Feses NOTIFICATION-TYPE
    OBJECTS { rptEvtPeriod, rptEvtValue, rptEvtVldty, rptEvtDateTime, rptEvtObjType, rptEvtParaLen, rptEvtPara}
    STATUS current
    DESCRIPTION
        "Trap of PerEvt: OTU4 SM Far Severely Errored Second"
    ::= { optixTrapsPER  15119}

--  1.3.6.1.4.1.2011.2.25.3.40.40.30.15120
    perEvtOtu4Feuas NOTIFICATION-TYPE
    OBJECTS { rptEvtPeriod, rptEvtValue, rptEvtVldty, rptEvtDateTime, rptEvtObjType, rptEvtParaLen, rptEvtPara}
    STATUS current
    DESCRIPTION
        "Trap of PerEvt: OTU4 SM Far Unavailable Seconds"
    ::= { optixTrapsPER  15120}

--  1.3.6.1.4.1.2011.2.25.3.40.40.30.15121
    perEvtOtu4Fesesr NOTIFICATION-TYPE
    OBJECTS { rptEvtPeriod, rptEvtValue, rptEvtVldty, rptEvtDateTime, rptEvtObjType, rptEvtParaLen, rptEvtPara}
    STATUS current
    DESCRIPTION
        "Trap of PerEvt: OTU4 SM Far Severely Errored Second Ratio"
    ::= { optixTrapsPER  15121}

--  1.3.6.1.4.1.2011.2.25.3.40.40.30.15122
    perEvtOtu4Febber NOTIFICATION-TYPE
    OBJECTS { rptEvtPeriod, rptEvtValue, rptEvtVldty, rptEvtDateTime, rptEvtObjType, rptEvtParaLen, rptEvtPara}
    STATUS current
    DESCRIPTION
        "Trap of PerEvt: OTU4 SM Far Background Block Error Ratio"
    ::= { optixTrapsPER  15122}

--  1.3.6.1.4.1.2011.2.25.3.40.40.30.15123
    perEvtOdu4Pmbbe NOTIFICATION-TYPE
    OBJECTS { rptEvtPeriod, rptEvtValue, rptEvtVldty, rptEvtDateTime, rptEvtObjType, rptEvtParaLen, rptEvtPara}
    STATUS current
    DESCRIPTION
        "Trap of PerEvt: ODU4 PM Background Block Error"
    ::= { optixTrapsPER  15123}

--  1.3.6.1.4.1.2011.2.25.3.40.40.30.15124
    perEvtOdu4Pmes NOTIFICATION-TYPE
    OBJECTS { rptEvtPeriod, rptEvtValue, rptEvtVldty, rptEvtDateTime, rptEvtObjType, rptEvtParaLen, rptEvtPara}
    STATUS current
    DESCRIPTION
        "Trap of PerEvt: ODU4 PM Errored Second"
    ::= { optixTrapsPER  15124}

--  1.3.6.1.4.1.2011.2.25.3.40.40.30.15125
    perEvtOdu4Pmses NOTIFICATION-TYPE
    OBJECTS { rptEvtPeriod, rptEvtValue, rptEvtVldty, rptEvtDateTime, rptEvtObjType, rptEvtParaLen, rptEvtPara}
    STATUS current
    DESCRIPTION
        "Trap of PerEvt: ODU4 PM Severely Errored Second"
    ::= { optixTrapsPER  15125}

--  1.3.6.1.4.1.2011.2.25.3.40.40.30.15126
    perEvtOtu4Pmuas NOTIFICATION-TYPE
    OBJECTS { rptEvtPeriod, rptEvtValue, rptEvtVldty, rptEvtDateTime, rptEvtObjType, rptEvtParaLen, rptEvtPara}
    STATUS current
    DESCRIPTION
        "Trap of PerEvt: ODU4 PM Unavailable Seconds"
    ::= { optixTrapsPER  15126}

--  1.3.6.1.4.1.2011.2.25.3.40.40.30.15127
    perEvtOdu4Pmsesr NOTIFICATION-TYPE
    OBJECTS { rptEvtPeriod, rptEvtValue, rptEvtVldty, rptEvtDateTime, rptEvtObjType, rptEvtParaLen, rptEvtPara}
    STATUS current
    DESCRIPTION
        "Trap of PerEvt: ODU4 PM Severely Errored Second Ratio"
    ::= { optixTrapsPER  15127}

--  1.3.6.1.4.1.2011.2.25.3.40.40.30.15128
    perEvtOdu4Pmbber NOTIFICATION-TYPE
    OBJECTS { rptEvtPeriod, rptEvtValue, rptEvtVldty, rptEvtDateTime, rptEvtObjType, rptEvtParaLen, rptEvtPara}
    STATUS current
    DESCRIPTION
        "Trap of PerEvt: ODU4 PM Background Block Error Ratio"
    ::= { optixTrapsPER  15128}

--  1.3.6.1.4.1.2011.2.25.3.40.40.30.15129
    perEvtOdu4Pmfebbe NOTIFICATION-TYPE
    OBJECTS { rptEvtPeriod, rptEvtValue, rptEvtVldty, rptEvtDateTime, rptEvtObjType, rptEvtParaLen, rptEvtPara}
    STATUS current
    DESCRIPTION
        "Trap of PerEvt: ODU4 PM Far Background Block Error"
    ::= { optixTrapsPER  15129}

--  1.3.6.1.4.1.2011.2.25.3.40.40.30.15130
    perEvtOdu4Pmfees NOTIFICATION-TYPE
    OBJECTS { rptEvtPeriod, rptEvtValue, rptEvtVldty, rptEvtDateTime, rptEvtObjType, rptEvtParaLen, rptEvtPara}
    STATUS current
    DESCRIPTION
        "Trap of PerEvt: ODU4 PM Far Errored Second"
    ::= { optixTrapsPER  15130}

--  1.3.6.1.4.1.2011.2.25.3.40.40.30.15131
    perEvtOdu4Pmfeses NOTIFICATION-TYPE
    OBJECTS { rptEvtPeriod, rptEvtValue, rptEvtVldty, rptEvtDateTime, rptEvtObjType, rptEvtParaLen, rptEvtPara}
    STATUS current
    DESCRIPTION
        "Trap of PerEvt: ODU4 PM Far Severely Errored Second"
    ::= { optixTrapsPER  15131}

--  1.3.6.1.4.1.2011.2.25.3.40.40.30.15132
    perEvtOdu4Pmfeuas NOTIFICATION-TYPE
    OBJECTS { rptEvtPeriod, rptEvtValue, rptEvtVldty, rptEvtDateTime, rptEvtObjType, rptEvtParaLen, rptEvtPara}
    STATUS current
    DESCRIPTION
        "Trap of PerEvt: ODU4 PM Far Unavailable Seconds"
    ::= { optixTrapsPER  15132}

--  1.3.6.1.4.1.2011.2.25.3.40.40.30.15133
    perEvtOdu4Pmfesesr NOTIFICATION-TYPE
    OBJECTS { rptEvtPeriod, rptEvtValue, rptEvtVldty, rptEvtDateTime, rptEvtObjType, rptEvtParaLen, rptEvtPara}
    STATUS current
    DESCRIPTION
        "Trap of PerEvt: ODU4 PM Far Severely Errored Second Ratio"
    ::= { optixTrapsPER  15133}

--  1.3.6.1.4.1.2011.2.25.3.40.40.30.15134
    perEvtOdu4Pmfebber NOTIFICATION-TYPE
    OBJECTS { rptEvtPeriod, rptEvtValue, rptEvtVldty, rptEvtDateTime, rptEvtObjType, rptEvtParaLen, rptEvtPara}
    STATUS current
    DESCRIPTION
        "Trap of PerEvt: ODU4 PM Far Background Block Error Ratio"
    ::= { optixTrapsPER  15134}
--  1.3.6.1.4.1.2011.2.25.3.40.40.30.15378
    perEvtpmdmax NOTIFICATION-TYPE
    OBJECTS { rptEvtPeriod, rptEvtValue, rptEvtVldty, rptEvtDateTime, rptEvtObjType, rptEvtParaLen, rptEvtPara}
    STATUS current
    DESCRIPTION
        "Trap of PerEvt: Polarization mode dispersion Maximum"
    ::= { optixTrapsPER  15378}

--  1.3.6.1.4.1.2011.2.25.3.40.40.30.15379
    perEvtpmdmin NOTIFICATION-TYPE
    OBJECTS { rptEvtPeriod, rptEvtValue, rptEvtVldty, rptEvtDateTime, rptEvtObjType, rptEvtParaLen, rptEvtPara}
    STATUS current
    DESCRIPTION
        "Trap of PerEvt: Polarization mode dispersion Minimum"
    ::= { optixTrapsPER  15379}

--  1.3.6.1.4.1.2011.2.25.3.40.40.30.15380
    perEvtpmdcur NOTIFICATION-TYPE
    OBJECTS { rptEvtPeriod, rptEvtValue, rptEvtVldty, rptEvtDateTime, rptEvtObjType, rptEvtParaLen, rptEvtPara}
    STATUS current
    DESCRIPTION
        "Trap of PerEvt: Polarization mode dispersion Cur-Value"
    ::= { optixTrapsPER  15380}

--  1.3.6.1.4.1.2011.2.25.3.40.40.30.15416
    perEvtpmdavg NOTIFICATION-TYPE
    OBJECTS { rptEvtPeriod, rptEvtValue, rptEvtVldty, rptEvtDateTime, rptEvtObjType, rptEvtParaLen, rptEvtPara}
    STATUS current
    DESCRIPTION
        "Trap of PerEvt: Polarization mode average dispersion"
    ::= { optixTrapsPER  15416}

--  1.3.6.1.4.1.2011.2.25.3.40.40.30.15381
    perEvtpeakInpowerMax NOTIFICATION-TYPE
    OBJECTS { rptEvtPeriod, rptEvtValue, rptEvtVldty, rptEvtDateTime, rptEvtObjType, rptEvtParaLen, rptEvtPara}
    STATUS current
    DESCRIPTION
        "Trap of PerEvt: Maximum peak input optical power"
    ::= { optixTrapsPER  15381}

--  1.3.6.1.4.1.2011.2.25.3.40.40.30.15382
    perEvtpeakInpowerCur NOTIFICATION-TYPE
    OBJECTS { rptEvtPeriod, rptEvtValue, rptEvtVldty, rptEvtDateTime, rptEvtObjType, rptEvtParaLen, rptEvtPara}
    STATUS current
    DESCRIPTION
        "Trap of PerEvt: Current peak input optical power"
    ::= { optixTrapsPER  15382}

--  1.3.6.1.4.1.2011.2.25.3.40.40.30.15383
    perEvtpeakInpowerMin NOTIFICATION-TYPE
    OBJECTS { rptEvtPeriod, rptEvtValue, rptEvtVldty, rptEvtDateTime, rptEvtObjType, rptEvtParaLen, rptEvtPara}
    STATUS current
    DESCRIPTION
        "Trap of PerEvt: Minimum peak input optical power"
    ::= { optixTrapsPER  15383}

--  1.3.6.1.4.1.2011.2.25.3.40.40.30.15384
    perEvtvalleyInpowerMax NOTIFICATION-TYPE
    OBJECTS { rptEvtPeriod, rptEvtValue, rptEvtVldty, rptEvtDateTime, rptEvtObjType, rptEvtParaLen, rptEvtPara}
    STATUS current
    DESCRIPTION
        "Trap of PerEvt: Maximum valley input optical power"
    ::= { optixTrapsPER  15384}

--  1.3.6.1.4.1.2011.2.25.3.40.40.30.15385
    perEvtvalleyInpowerCur NOTIFICATION-TYPE
    OBJECTS { rptEvtPeriod, rptEvtValue, rptEvtVldty, rptEvtDateTime, rptEvtObjType, rptEvtParaLen, rptEvtPara}
    STATUS current
    DESCRIPTION
        "Trap of PerEvt: Current valley input optical power"
    ::= { optixTrapsPER  15385}

--  1.3.6.1.4.1.2011.2.25.3.40.40.30.15386
    perEvtvalleyInpowerMin NOTIFICATION-TYPE
    OBJECTS { rptEvtPeriod, rptEvtValue, rptEvtVldty, rptEvtDateTime, rptEvtObjType, rptEvtParaLen, rptEvtPara}
    STATUS current
    DESCRIPTION
        "Trap of PerEvt: Minimum valley input optical power"
    ::= { optixTrapsPER  15386}

--  1.3.6.1.4.1.2011.2.25.3.40.40.30.15387
    perEvtpeakOutpowerMax NOTIFICATION-TYPE
    OBJECTS { rptEvtPeriod, rptEvtValue, rptEvtVldty, rptEvtDateTime, rptEvtObjType, rptEvtParaLen, rptEvtPara}
    STATUS current
    DESCRIPTION
        "Trap of PerEvt: Maximum peak output optical power"
    ::= { optixTrapsPER  15387}

--  1.3.6.1.4.1.2011.2.25.3.40.40.30.15388
    perEvtpeakOutpowerCur NOTIFICATION-TYPE
    OBJECTS { rptEvtPeriod, rptEvtValue, rptEvtVldty, rptEvtDateTime, rptEvtObjType, rptEvtParaLen, rptEvtPara}
    STATUS current
    DESCRIPTION
        "Trap of PerEvt: Current peak output optical power"
    ::= { optixTrapsPER  15388}

--  1.3.6.1.4.1.2011.2.25.3.40.40.30.15389
    perEvtpeakOutpowerMin NOTIFICATION-TYPE
    OBJECTS { rptEvtPeriod, rptEvtValue, rptEvtVldty, rptEvtDateTime, rptEvtObjType, rptEvtParaLen, rptEvtPara}
    STATUS current
    DESCRIPTION
        "Trap of PerEvt: Minimum peak output optical power"
    ::= { optixTrapsPER  15389}

--  1.3.6.1.4.1.2011.2.25.3.40.40.30.15390
    perEvtvalleyOutpowerMax NOTIFICATION-TYPE
    OBJECTS { rptEvtPeriod, rptEvtValue, rptEvtVldty, rptEvtDateTime, rptEvtObjType, rptEvtParaLen, rptEvtPara}
    STATUS current
    DESCRIPTION
        "Trap of PerEvt: Maximum valley output optical power"
    ::= { optixTrapsPER  15390}

--  1.3.6.1.4.1.2011.2.25.3.40.40.30.15391
    perEvtvalleyOutpowerCur NOTIFICATION-TYPE
    OBJECTS { rptEvtPeriod, rptEvtValue, rptEvtVldty, rptEvtDateTime, rptEvtObjType, rptEvtParaLen, rptEvtPara}
    STATUS current
    DESCRIPTION
        "Trap of PerEvt: Current valley output optical power"
    ::= { optixTrapsPER  15391}

--  1.3.6.1.4.1.2011.2.25.3.40.40.30.15392
    perEvtvalleyOutpowerMin NOTIFICATION-TYPE
    OBJECTS { rptEvtPeriod, rptEvtValue, rptEvtVldty, rptEvtDateTime, rptEvtObjType, rptEvtParaLen, rptEvtPara}
    STATUS current
    DESCRIPTION
        "Trap of PerEvt: Minimum valley output optical power"
    ::= { optixTrapsPER  15392}
--  1.3.6.1.4.1.2011.2.25.3.40.40.30.15439
    perEvtodu2Pmtmp NOTIFICATION-TYPE
    OBJECTS { rptEvtPeriod, rptEvtValue, rptEvtVldty, rptEvtDateTime, rptEvtObjType, rptEvtParaLen, rptEvtPara}
    STATUS current
    DESCRIPTION
        "Trap of PerEvt: ODU2 PM Section Total Monitor Period"
    ::= { optixTrapsPER  15439}
--  1.3.6.1.4.1.2011.2.25.3.40.40.30.15447
    perEvtodu3Pmtmp NOTIFICATION-TYPE
    OBJECTS { rptEvtPeriod, rptEvtValue, rptEvtVldty, rptEvtDateTime, rptEvtObjType, rptEvtParaLen, rptEvtPara}
    STATUS current
    DESCRIPTION
        "Trap of PerEvt: ODU3 PM Section Total Monitor Period"
    ::= { optixTrapsPER  15447}
--  1.3.6.1.4.1.2011.2.25.3.40.40.30.15454
    perEvtotu4Tmp NOTIFICATION-TYPE
    OBJECTS { rptEvtPeriod, rptEvtValue, rptEvtVldty, rptEvtDateTime, rptEvtObjType, rptEvtParaLen, rptEvtPara}
    STATUS current
    DESCRIPTION
        "Trap of PerEvt: OTU4 Total Monitor Period"
    ::= { optixTrapsPER  15454}

--  1.3.6.1.4.1.2011.2.25.3.40.40.30.15455
    perEvtodu4Pmtmp NOTIFICATION-TYPE
    OBJECTS { rptEvtPeriod, rptEvtValue, rptEvtVldty, rptEvtDateTime, rptEvtObjType, rptEvtParaLen, rptEvtPara}
    STATUS current
    DESCRIPTION
        "Trap of PerEvt: ODU4 PM Section Total Monitor Period"
    ::= { optixTrapsPER  15455}
    --  1.3.6.1.4.1.2011.2.25.3.40.40.30.15601
    perEvtethBbe NOTIFICATION-TYPE
    OBJECTS { rptEvtPeriod, rptEvtValue, rptEvtVldty, rptEvtDateTime, rptEvtObjType, rptEvtParaLen, rptEvtPara}
    STATUS current
    DESCRIPTION
        "Trap of PerEvt: 40GE/100GE Background Block Error"
    ::= { optixTrapsPER  15601}

    --  1.3.6.1.4.1.2011.2.25.3.40.40.30.15602
    perEvtethBber NOTIFICATION-TYPE
    OBJECTS { rptEvtPeriod, rptEvtValue, rptEvtVldty, rptEvtDateTime, rptEvtObjType, rptEvtParaLen, rptEvtPara}
    STATUS current
    DESCRIPTION
         "Trap of PerEvt: 40GE/100GE Background Block Error Ratio"
    ::= { optixTrapsPER  15602}

    --  1.3.6.1.4.1.2011.2.25.3.40.40.30.15603
    perEvtethSesr NOTIFICATION-TYPE
    OBJECTS { rptEvtPeriod, rptEvtValue, rptEvtVldty, rptEvtDateTime, rptEvtObjType, rptEvtParaLen, rptEvtPara}
    STATUS current
    DESCRIPTION
         "Trap of PerEvt: 40GE/100GE Severely Errored Second Ratio"
    ::= { optixTrapsPER  15603}

    --  1.3.6.1.4.1.2011.2.25.3.40.40.30.15604
    perEvtethUas NOTIFICATION-TYPE
    OBJECTS { rptEvtPeriod, rptEvtValue, rptEvtVldty, rptEvtDateTime, rptEvtObjType, rptEvtParaLen, rptEvtPara}
    STATUS current
    DESCRIPTION
         "Trap of PerEvt: 40GE/100GE Unavailable Seconds"
    ::= { optixTrapsPER  15604}

    --  1.3.6.1.4.1.2011.2.25.3.40.40.30.15605
    perEvtethEs NOTIFICATION-TYPE
    OBJECTS { rptEvtPeriod, rptEvtValue, rptEvtVldty, rptEvtDateTime, rptEvtObjType, rptEvtParaLen, rptEvtPara}
    STATUS current
    DESCRIPTION
        "Trap of PerEvt: 40GE/100GE Errored Second"
    ::= { optixTrapsPER  15605}

    --  1.3.6.1.4.1.2011.2.25.3.40.40.30.15606
    perEvtethSes NOTIFICATION-TYPE
    OBJECTS { rptEvtPeriod, rptEvtValue, rptEvtVldty, rptEvtDateTime, rptEvtObjType, rptEvtParaLen, rptEvtPara}
    STATUS current
    DESCRIPTION
        "Trap of PerEvt: 40GE/100GE Severely Errored Second"
    ::= { optixTrapsPER  15606}

    --  1.3.6.1.4.1.2011.2.25.3.40.40.30.15627
    perEvtOtucnBbe NOTIFICATION-TYPE
    OBJECTS { rptEvtPeriod, rptEvtValue, rptEvtVldty, rptEvtDateTime, rptEvtObjType, rptEvtParaLen, rptEvtPara}
    STATUS current
    DESCRIPTION
         "OTUCn SM Background Block Error"
    ::= { optixTrapsPER  15627}

    --  1.3.6.1.4.1.2011.2.25.3.40.40.30.15628
    perEvtOtucnFees NOTIFICATION-TYPE
    OBJECTS { rptEvtPeriod, rptEvtValue, rptEvtVldty, rptEvtDateTime, rptEvtObjType, rptEvtParaLen, rptEvtPara}
    STATUS current
    DESCRIPTION
         "OTUCn SM Far Errored Second"
    ::= { optixTrapsPER  15628}

    --  1.3.6.1.4.1.2011.2.25.3.40.40.30.15629
    perEvtOtucnFebbe NOTIFICATION-TYPE
    OBJECTS { rptEvtPeriod, rptEvtValue, rptEvtVldty, rptEvtDateTime, rptEvtObjType, rptEvtParaLen, rptEvtPara}
    STATUS current
    DESCRIPTION
         "OTUCn SM Far Background Block Error"
    ::= { optixTrapsPER  15629}

    --  1.3.6.1.4.1.2011.2.25.3.40.40.30.15630
    perEvtOtucnBber NOTIFICATION-TYPE
    OBJECTS { rptEvtPeriod, rptEvtValue, rptEvtVldty, rptEvtDateTime, rptEvtObjType, rptEvtParaLen, rptEvtPara}
    STATUS current
    DESCRIPTION
         "OTUCn SM Background Block Error Ratio"
    ::= { optixTrapsPER  15630}

    --  1.3.6.1.4.1.2011.2.25.3.40.40.30.15631
    perEvtOtucnSesr NOTIFICATION-TYPE
    OBJECTS { rptEvtPeriod, rptEvtValue, rptEvtVldty, rptEvtDateTime, rptEvtObjType, rptEvtParaLen, rptEvtPara}
    STATUS current
    DESCRIPTION
         "OTUCn SM Severely Errored Second Ratio"
    ::= { optixTrapsPER  15631}

    --  1.3.6.1.4.1.2011.2.25.3.40.40.30.15632
    perEvtOtucnFeses NOTIFICATION-TYPE
    OBJECTS { rptEvtPeriod, rptEvtValue, rptEvtVldty, rptEvtDateTime, rptEvtObjType, rptEvtParaLen, rptEvtPara}
    STATUS current
    DESCRIPTION
         "OTUCn SM Far Severely Errored Second"
    ::= { optixTrapsPER  15632}

    --  1.3.6.1.4.1.2011.2.25.3.40.40.30.15633
    perEvtOtucnBiaes NOTIFICATION-TYPE
    OBJECTS { rptEvtPeriod, rptEvtValue, rptEvtVldty, rptEvtDateTime, rptEvtObjType, rptEvtParaLen, rptEvtPara}
    STATUS current
    DESCRIPTION
         "OTUCn SM Backward Incoming Alignment Errored Second "
    ::= { optixTrapsPER  15633}

    --  1.3.6.1.4.1.2011.2.25.3.40.40.30.15634
    perEvtOtucnUas NOTIFICATION-TYPE
    OBJECTS { rptEvtPeriod, rptEvtValue, rptEvtVldty, rptEvtDateTime, rptEvtObjType, rptEvtParaLen, rptEvtPara}
    STATUS current
    DESCRIPTION
         "OTUCn SM Unavailable Seconds"
    ::= { optixTrapsPER  15634}

    --  1.3.6.1.4.1.2011.2.25.3.40.40.30.15635
    perEvtOtucnSes NOTIFICATION-TYPE
    OBJECTS { rptEvtPeriod, rptEvtValue, rptEvtVldty, rptEvtDateTime, rptEvtObjType, rptEvtParaLen, rptEvtPara}
    STATUS current
    DESCRIPTION
         "OTUCn SM Severely Errored Second"
    ::= { optixTrapsPER  15635}

    --  1.3.6.1.4.1.2011.2.25.3.40.40.30.15636
    perEvtOtucnEs NOTIFICATION-TYPE
    OBJECTS { rptEvtPeriod, rptEvtValue, rptEvtVldty, rptEvtDateTime, rptEvtObjType, rptEvtParaLen, rptEvtPara}
    STATUS current
    DESCRIPTION
         "OTUCn SM Errored Second"
    ::= { optixTrapsPER  15636}

    --  1.3.6.1.4.1.2011.2.25.3.40.40.30.15637
    perEvtOtucnIaes NOTIFICATION-TYPE
    OBJECTS { rptEvtPeriod, rptEvtValue, rptEvtVldty, rptEvtDateTime, rptEvtObjType, rptEvtParaLen, rptEvtPara}
    STATUS current
    DESCRIPTION
         "OTUCn SM Incoming Alignment Errored Second"
    ::= { optixTrapsPER  15637}

    --  1.3.6.1.4.1.2011.2.25.3.40.40.30.15638
    perEvtOtucnFebber NOTIFICATION-TYPE
    OBJECTS { rptEvtPeriod, rptEvtValue, rptEvtVldty, rptEvtDateTime, rptEvtObjType, rptEvtParaLen, rptEvtPara}
    STATUS current
    DESCRIPTION
         "OTUCn SM Far Background Block Error Ratio"
    ::= { optixTrapsPER  15638}

    --  1.3.6.1.4.1.2011.2.25.3.40.40.30.15639
    perEvtOtucnFeuas NOTIFICATION-TYPE
    OBJECTS { rptEvtPeriod, rptEvtValue, rptEvtVldty, rptEvtDateTime, rptEvtObjType, rptEvtParaLen, rptEvtPara}
    STATUS current
    DESCRIPTION
         "OTUCn SM Far Unavailable Seconds"
    ::= { optixTrapsPER  15639}

    --  1.3.6.1.4.1.2011.2.25.3.40.40.30.15640
    perEvtOtucnTmp NOTIFICATION-TYPE
    OBJECTS { rptEvtPeriod, rptEvtValue, rptEvtVldty, rptEvtDateTime, rptEvtObjType, rptEvtParaLen, rptEvtPara}
    STATUS current
    DESCRIPTION
         "OTUCn Total Monitor Period"
    ::= { optixTrapsPER  15640}

    --  1.3.6.1.4.1.2011.2.25.3.40.40.30.15641
    perEvtOtucnFesesr NOTIFICATION-TYPE
    OBJECTS { rptEvtPeriod, rptEvtValue, rptEvtVldty, rptEvtDateTime, rptEvtObjType, rptEvtParaLen, rptEvtPara}
    STATUS current
    DESCRIPTION
         "OTUCn SM Far Severely Errored Second Ratio"
    ::= { optixTrapsPER  15641}

    --  1.3.6.1.4.1.2011.2.25.3.40.40.30.15642
    perEvtOducnPmFesesr NOTIFICATION-TYPE
    OBJECTS { rptEvtPeriod, rptEvtValue, rptEvtVldty, rptEvtDateTime, rptEvtObjType, rptEvtParaLen, rptEvtPara}
    STATUS current
    DESCRIPTION
         "ODUCn PM Far Severely Errored Second Ratio"
    ::= { optixTrapsPER  15642}

    --  1.3.6.1.4.1.2011.2.25.3.40.40.30.15643
    perEvtOducnPmFebber NOTIFICATION-TYPE
    OBJECTS { rptEvtPeriod, rptEvtValue, rptEvtVldty, rptEvtDateTime, rptEvtObjType, rptEvtParaLen, rptEvtPara}
    STATUS current
    DESCRIPTION
         "ODUCn PM Far Background Block Error Ratio"
    ::= { optixTrapsPER  15643}

    --  1.3.6.1.4.1.2011.2.25.3.40.40.30.15644
    perEvtOducnPmFees NOTIFICATION-TYPE
    OBJECTS { rptEvtPeriod, rptEvtValue, rptEvtVldty, rptEvtDateTime, rptEvtObjType, rptEvtParaLen, rptEvtPara}
    STATUS current
    DESCRIPTION
         "ODUCn PM Far Errored Second"
    ::= { optixTrapsPER  15644}

    --  1.3.6.1.4.1.2011.2.25.3.40.40.30.15645
    perEvtOducnPmFeses NOTIFICATION-TYPE
    OBJECTS { rptEvtPeriod, rptEvtValue, rptEvtVldty, rptEvtDateTime, rptEvtObjType, rptEvtParaLen, rptEvtPara}
    STATUS current
    DESCRIPTION
         "ODUCn PM Far Severely Errored Second"
    ::= { optixTrapsPER  15645}

    --  1.3.6.1.4.1.2011.2.25.3.40.40.30.15646
    perEvtOducnPmFeuas NOTIFICATION-TYPE
    OBJECTS { rptEvtPeriod, rptEvtValue, rptEvtVldty, rptEvtDateTime, rptEvtObjType, rptEvtParaLen, rptEvtPara}
    STATUS current
    DESCRIPTION
         "ODUCn PM Far Unavailable Seconds "
    ::= { optixTrapsPER  15646}

    --  1.3.6.1.4.1.2011.2.25.3.40.40.30.15647
    perEvtOducnPmEs NOTIFICATION-TYPE
    OBJECTS { rptEvtPeriod, rptEvtValue, rptEvtVldty, rptEvtDateTime, rptEvtObjType, rptEvtParaLen, rptEvtPara}
    STATUS current
    DESCRIPTION
         "ODUCn PM Errored Second"
    ::= { optixTrapsPER  15647}

    --  1.3.6.1.4.1.2011.2.25.3.40.40.30.15648
    perEvtOducnPmSes NOTIFICATION-TYPE
    OBJECTS { rptEvtPeriod, rptEvtValue, rptEvtVldty, rptEvtDateTime, rptEvtObjType, rptEvtParaLen, rptEvtPara}
    STATUS current
    DESCRIPTION
         "ODUCn PM Severely Errored Second"
    ::= { optixTrapsPER  15648}

    --  1.3.6.1.4.1.2011.2.25.3.40.40.30.15649
    perEvtOducnPmBbe NOTIFICATION-TYPE
    OBJECTS { rptEvtPeriod, rptEvtValue, rptEvtVldty, rptEvtDateTime, rptEvtObjType, rptEvtParaLen, rptEvtPara}
    STATUS current
    DESCRIPTION
         "ODUCn PM Background Block Error"
    ::= { optixTrapsPER  15649}

    --  1.3.6.1.4.1.2011.2.25.3.40.40.30.15650
    perEvtOducnPmBber NOTIFICATION-TYPE
    OBJECTS { rptEvtPeriod, rptEvtValue, rptEvtVldty, rptEvtDateTime, rptEvtObjType, rptEvtParaLen, rptEvtPara}
    STATUS current
    DESCRIPTION
         "ODUCn PM Background Block Error Ratio"
    ::= { optixTrapsPER  15650}

    --  1.3.6.1.4.1.2011.2.25.3.40.40.30.15651
    perEvtOducnPmFebbe NOTIFICATION-TYPE
    OBJECTS { rptEvtPeriod, rptEvtValue, rptEvtVldty, rptEvtDateTime, rptEvtObjType, rptEvtParaLen, rptEvtPara}
    STATUS current
    DESCRIPTION
         "ODUCn PM Far Background Block Error"
    ::= { optixTrapsPER  15651}

    --  1.3.6.1.4.1.2011.2.25.3.40.40.30.15652
    perEvtOducnPmUas NOTIFICATION-TYPE
    OBJECTS { rptEvtPeriod, rptEvtValue, rptEvtVldty, rptEvtDateTime, rptEvtObjType, rptEvtParaLen, rptEvtPara}
    STATUS current
    DESCRIPTION
         "ODUCn PM Unavailable Seconds"
    ::= { optixTrapsPER  15652}

    --  1.3.6.1.4.1.2011.2.25.3.40.40.30.15653
    perEvtOducnPmSesr NOTIFICATION-TYPE
    OBJECTS { rptEvtPeriod, rptEvtValue, rptEvtVldty, rptEvtDateTime, rptEvtObjType, rptEvtParaLen, rptEvtPara}
    STATUS current
    DESCRIPTION
         "ODUCn PM Severely Errored Second Ratio"
    ::= { optixTrapsPER  15653}

    --  1.3.6.1.4.1.2011.2.25.3.40.40.30.15654
    perEvtOducnPmTmp NOTIFICATION-TYPE
    OBJECTS { rptEvtPeriod, rptEvtValue, rptEvtVldty, rptEvtDateTime, rptEvtObjType, rptEvtParaLen, rptEvtPara}
    STATUS current
    DESCRIPTION
         "ODUCn PM Section Total Monitor Period"
    ::= { optixTrapsPER  15654}

    --  1.3.6.1.4.1.2011.2.25.3.40.40.30.15883
    perEvtlanelsoopmax NOTIFICATION-TYPE
    OBJECTS { rptEvtPeriod, rptEvtValue, rptEvtVldty, rptEvtDateTime, rptEvtObjType, rptEvtParaLen, rptEvtPara}
    STATUS current
    DESCRIPTION
        "Trap of PerEvt: Maximum laser output power on the sub-channel"
    ::= { optixTrapsPER  15883}

    --  1.3.6.1.4.1.2011.2.25.3.40.40.30.15884
    perEvtlanelsoopmin NOTIFICATION-TYPE
    OBJECTS { rptEvtPeriod, rptEvtValue, rptEvtVldty, rptEvtDateTime, rptEvtObjType, rptEvtParaLen, rptEvtPara}
    STATUS current
    DESCRIPTION
        "Trap of PerEvt: Minimum laser output power on the sub-channel"
    ::= { optixTrapsPER  15884}

    --  1.3.6.1.4.1.2011.2.25.3.40.40.30.15885
    perEvtlanelsoopcur NOTIFICATION-TYPE
    OBJECTS { rptEvtPeriod, rptEvtValue, rptEvtVldty, rptEvtDateTime, rptEvtObjType, rptEvtParaLen, rptEvtPara}
    STATUS current
    DESCRIPTION
        "Trap of PerEvt: Current laser output power on the sub-channel"
    ::= { optixTrapsPER  15885}

    --  1.3.6.1.4.1.2011.2.25.3.40.40.30.15886
    perEvtlanelsiopmax NOTIFICATION-TYPE
    OBJECTS { rptEvtPeriod, rptEvtValue, rptEvtVldty, rptEvtDateTime, rptEvtObjType, rptEvtParaLen, rptEvtPara}
    STATUS current
    DESCRIPTION
        "Trap of PerEvt: Maximum laser input power on the sub-channel"
    ::= { optixTrapsPER  15886}

    --  1.3.6.1.4.1.2011.2.25.3.40.40.30.15887
    perEvtlanelsiopmin NOTIFICATION-TYPE
    OBJECTS { rptEvtPeriod, rptEvtValue, rptEvtVldty, rptEvtDateTime, rptEvtObjType, rptEvtParaLen, rptEvtPara}
    STATUS current
    DESCRIPTION
        "Trap of PerEvt: Minimum laser input power on the sub-channel"
    ::= { optixTrapsPER  15887}

    --  1.3.6.1.4.1.2011.2.25.3.40.40.30.15888
    perEvtlanelsiopcur NOTIFICATION-TYPE
    OBJECTS { rptEvtPeriod, rptEvtValue, rptEvtVldty, rptEvtDateTime, rptEvtObjType, rptEvtParaLen, rptEvtPara}
    STATUS current
    DESCRIPTION
        "Trap of PerEvt: Current laser input power on the sub-channel"
    ::= { optixTrapsPER  15888}

    --  1.3.6.1.4.1.2011.2.25.3.40.40.30.15889
    perEvtlanelsbiasmax NOTIFICATION-TYPE
    OBJECTS { rptEvtPeriod, rptEvtValue, rptEvtVldty, rptEvtDateTime, rptEvtObjType, rptEvtParaLen, rptEvtPara}
    STATUS current
    DESCRIPTION
        "Trap of PerEvt: Maximum laser bias currentof the laser on the sub-channel"
    ::= { optixTrapsPER  15889}

    --  1.3.6.1.4.1.2011.2.25.3.40.40.30.15890
    perEvtlanelsbiasmin NOTIFICATION-TYPE
    OBJECTS { rptEvtPeriod, rptEvtValue, rptEvtVldty, rptEvtDateTime, rptEvtObjType, rptEvtParaLen, rptEvtPara}
    STATUS current
    DESCRIPTION
        "Trap of PerEvt: Minimum laser bias current on the sub-channel"
    ::= { optixTrapsPER  15890}

    --  1.3.6.1.4.1.2011.2.25.3.40.40.30.15891
    perEvtlanelsbiascur NOTIFICATION-TYPE
    OBJECTS { rptEvtPeriod, rptEvtValue, rptEvtVldty, rptEvtDateTime, rptEvtObjType, rptEvtParaLen, rptEvtPara}
    STATUS current
    DESCRIPTION
        "Trap of PerEvt: Current laser bias current on the sub-channel"
    ::= { optixTrapsPER  15891}

	--  1.3.6.1.4.1.2011.2.25.3.40.40.30.1
    perEvtRsbbe NOTIFICATION-TYPE
        OBJECTS { rptEvtPeriod, rptEvtValue, rptEvtVldty, rptEvtDateTime, rptEvtObjType, rptEvtParaLen, rptEvtPara}
        STATUS current
        DESCRIPTION
        "Trap of PerEvt: Regenerator section background block error"
        ::= { optixTrapsPER  1 }

--  1.3.6.1.4.1.2011.2.25.3.40.40.30.2
    perEvtRses NOTIFICATION-TYPE
        OBJECTS { rptEvtPeriod, rptEvtValue, rptEvtVldty, rptEvtDateTime, rptEvtObjType, rptEvtParaLen, rptEvtPara}
        STATUS current
        DESCRIPTION
        "Trap of PerEvt: Regenerator section errored seconds"
        ::= { optixTrapsPER  2 }

--  1.3.6.1.4.1.2011.2.25.3.40.40.30.3
    perEvtRsses NOTIFICATION-TYPE
        OBJECTS { rptEvtPeriod, rptEvtValue, rptEvtVldty, rptEvtDateTime, rptEvtObjType, rptEvtParaLen, rptEvtPara}
        STATUS current
        DESCRIPTION
        "Trap of PerEvt: Regenerator section severely errored seconds"
        ::= { optixTrapsPER  3 }

--  1.3.6.1.4.1.2011.2.25.3.40.40.30.7
    perEvtRscses NOTIFICATION-TYPE
        OBJECTS { rptEvtPeriod, rptEvtValue, rptEvtVldty, rptEvtDateTime, rptEvtObjType, rptEvtParaLen, rptEvtPara}
        STATUS current
        DESCRIPTION
        "Trap of PerEvt: Regenerator section consecutive severely errored seconds"
        ::= { optixTrapsPER  7 }

--  1.3.6.1.4.1.2011.2.25.3.40.40.30.15393
    perEvtPeakLstmpMax NOTIFICATION-TYPE
        OBJECTS { rptEvtPeriod, rptEvtValue, rptEvtVldty, rptEvtDateTime, rptEvtObjType, rptEvtParaLen, rptEvtPara}
        STATUS current
        DESCRIPTION
        "Trap of PerEvt: Maximum peak temperature of the laser on an optical module"
        ::= { optixTrapsPER  15393 }

--  1.3.6.1.4.1.2011.2.25.3.40.40.30.15394
    perEvtPeakLstmpCur NOTIFICATION-TYPE
        OBJECTS { rptEvtPeriod, rptEvtValue, rptEvtVldty, rptEvtDateTime, rptEvtObjType, rptEvtParaLen, rptEvtPara}
        STATUS current
        DESCRIPTION
        "Trap of PerEvt: Current peak temperature of the laser on an optical module"
        ::= { optixTrapsPER  15394 }

--  1.3.6.1.4.1.2011.2.25.3.40.40.30.15395
    perEvtPeakLstmpMin NOTIFICATION-TYPE
        OBJECTS { rptEvtPeriod, rptEvtValue, rptEvtVldty, rptEvtDateTime, rptEvtObjType, rptEvtParaLen, rptEvtPara}
        STATUS current
        DESCRIPTION
        "Trap of PerEvt: Minimum peak temperature of the laser on an optical module"
        ::= { optixTrapsPER  15395 }

--  1.3.6.1.4.1.2011.2.25.3.40.40.30.15396
    perEvtValleyLstmpMax NOTIFICATION-TYPE
        OBJECTS { rptEvtPeriod, rptEvtValue, rptEvtVldty, rptEvtDateTime, rptEvtObjType, rptEvtParaLen, rptEvtPara}
        STATUS current
        DESCRIPTION
        "Trap of PerEvt: Maximum valley temperature of the laser on an optical module"
        ::= { optixTrapsPER  15396 }

--  1.3.6.1.4.1.2011.2.25.3.40.40.30.15397
    perEvtValleyLstmpCur NOTIFICATION-TYPE
        OBJECTS { rptEvtPeriod, rptEvtValue, rptEvtVldty, rptEvtDateTime, rptEvtObjType, rptEvtParaLen, rptEvtPara}
        STATUS current
        DESCRIPTION
        "Trap of PerEvt: Current valley temperature of the laser on an optical module"
        ::= { optixTrapsPER  15397 }

--  1.3.6.1.4.1.2011.2.25.3.40.40.30.15398
    perEvtValleyLstmpMin NOTIFICATION-TYPE
        OBJECTS { rptEvtPeriod, rptEvtValue, rptEvtVldty, rptEvtDateTime, rptEvtObjType, rptEvtParaLen, rptEvtPara}
        STATUS current
        DESCRIPTION
        "Trap of PerEvt: Minimum valley temperature of the laser on an optical module"
        ::= { optixTrapsPER  15398 }

--  1.3.6.1.4.1.2011.2.25.3.40.40.30.15399
    perEvtPeakLsbiasMax NOTIFICATION-TYPE
        OBJECTS { rptEvtPeriod, rptEvtValue, rptEvtVldty, rptEvtDateTime, rptEvtObjType, rptEvtParaLen, rptEvtPara}
        STATUS current
        DESCRIPTION
        "Trap of PerEvt: Maximum peak bias current of the laser on an optical module"
        ::= { optixTrapsPER  15399 }

--  1.3.6.1.4.1.2011.2.25.3.40.40.30.15400
    perEvtPeakLsbiasCur NOTIFICATION-TYPE
        OBJECTS { rptEvtPeriod, rptEvtValue, rptEvtVldty, rptEvtDateTime, rptEvtObjType, rptEvtParaLen, rptEvtPara}
        STATUS current
        DESCRIPTION
        "Trap of PerEvt: Current peak bias current of the laser on an optical module"
        ::= { optixTrapsPER  15400 }

--  1.3.6.1.4.1.2011.2.25.3.40.40.30.15401
    perEvtPeakLsbiasMin NOTIFICATION-TYPE
        OBJECTS { rptEvtPeriod, rptEvtValue, rptEvtVldty, rptEvtDateTime, rptEvtObjType, rptEvtParaLen, rptEvtPara}
        STATUS current
        DESCRIPTION
        "Trap of PerEvt: Minimum peak bias current of the laser on an optical module"
        ::= { optixTrapsPER  15401 }

--  1.3.6.1.4.1.2011.2.25.3.40.40.30.15402
    perEvtValleyLsbiasMax NOTIFICATION-TYPE
        OBJECTS { rptEvtPeriod, rptEvtValue, rptEvtVldty, rptEvtDateTime, rptEvtObjType, rptEvtParaLen, rptEvtPara}
        STATUS current
        DESCRIPTION
        "Trap of PerEvt: Maximum valley bias current of the laser on an optical module"
        ::= { optixTrapsPER  15402 }

--  1.3.6.1.4.1.2011.2.25.3.40.40.30.15403
    perEvtValleyLsbiasCur NOTIFICATION-TYPE
        OBJECTS { rptEvtPeriod, rptEvtValue, rptEvtVldty, rptEvtDateTime, rptEvtObjType, rptEvtParaLen, rptEvtPara}
        STATUS current
        DESCRIPTION
        "Trap of PerEvt: Current valley bias current of the laser on an optical module"
        ::= { optixTrapsPER  15403 }

--  1.3.6.1.4.1.2011.2.25.3.40.40.30.15404
    perEvtValleyLsbiasMin NOTIFICATION-TYPE
        OBJECTS { rptEvtPeriod, rptEvtValue, rptEvtVldty, rptEvtDateTime, rptEvtObjType, rptEvtParaLen, rptEvtPara}
        STATUS current
        DESCRIPTION
        "Trap of PerEvt: Minimum valley bias current of the laser on an optical module"
        ::= { optixTrapsPER  15404 }

--  1.3.6.1.4.1.2011.2.25.3.40.40.30.15656
    perEvtCfpLsiopmax NOTIFICATION-TYPE
        OBJECTS { rptEvtPeriod, rptEvtValue, rptEvtVldty, rptEvtDateTime, rptEvtObjType, rptEvtParaLen, rptEvtPara}
        STATUS current
        DESCRIPTION
        "Trap of PerEvt: Maximum input optical power of the laser on the channel of the CFP module"
        ::= { optixTrapsPER  15656 }

--  1.3.6.1.4.1.2011.2.25.3.40.40.30.15657
    perEvtCfpLsiopmin NOTIFICATION-TYPE
        OBJECTS { rptEvtPeriod, rptEvtValue, rptEvtVldty, rptEvtDateTime, rptEvtObjType, rptEvtParaLen, rptEvtPara}
        STATUS current
        DESCRIPTION
        "Trap of PerEvt: Maximum input optical power of the laser on the channel of the CFP module"
        ::= { optixTrapsPER  15657 }

--  1.3.6.1.4.1.2011.2.25.3.40.40.30.15658
    perEvtCfpLsiopcur NOTIFICATION-TYPE
        OBJECTS { rptEvtPeriod, rptEvtValue, rptEvtVldty, rptEvtDateTime, rptEvtObjType, rptEvtParaLen, rptEvtPara}
        STATUS current
        DESCRIPTION
        "Trap of PerEvt: Current input optical power of the laser on the channel of the CFP module"
        ::= { optixTrapsPER  15658 }

--  1.3.6.1.4.1.2011.2.25.3.40.40.30.15660
    perEvtCfpLsoopmax NOTIFICATION-TYPE
        OBJECTS { rptEvtPeriod, rptEvtValue, rptEvtVldty, rptEvtDateTime, rptEvtObjType, rptEvtParaLen, rptEvtPara}
        STATUS current
        DESCRIPTION
        "Trap of PerEvt: Maximum output optical power of the laser on the channel of the CFP module"
        ::= { optixTrapsPER  15660 }

--  1.3.6.1.4.1.2011.2.25.3.40.40.30.15661
    perEvtCfpLsoopmin NOTIFICATION-TYPE
        OBJECTS { rptEvtPeriod, rptEvtValue, rptEvtVldty, rptEvtDateTime, rptEvtObjType, rptEvtParaLen, rptEvtPara}
        STATUS current
        DESCRIPTION
        "Trap of PerEvt: Minimum output optical power of the laser on the channel of the CFP module"
        ::= { optixTrapsPER  15661 }

--  1.3.6.1.4.1.2011.2.25.3.40.40.30.15662
    perEvtCfpLsoopcur NOTIFICATION-TYPE
        OBJECTS { rptEvtPeriod, rptEvtValue, rptEvtVldty, rptEvtDateTime, rptEvtObjType, rptEvtParaLen, rptEvtPara}
        STATUS current
        DESCRIPTION
        "Trap of PerEvt: Current output optical power of the laser on the channel of the CFP module"
        ::= { optixTrapsPER  15662 }

--  1.3.6.1.4.1.2011.2.25.3.40.40.30.15664
    perEvtCfpLstmpmax NOTIFICATION-TYPE
        OBJECTS { rptEvtPeriod, rptEvtValue, rptEvtVldty, rptEvtDateTime, rptEvtObjType, rptEvtParaLen, rptEvtPara}
        STATUS current
        DESCRIPTION
        "Trap of PerEvt: Maximum working temperature of the laser on the channel of the CFP module"
        ::= { optixTrapsPER  15664 }

--  1.3.6.1.4.1.2011.2.25.3.40.40.30.15665
    perEvtCfpLstmpmin NOTIFICATION-TYPE
        OBJECTS { rptEvtPeriod, rptEvtValue, rptEvtVldty, rptEvtDateTime, rptEvtObjType, rptEvtParaLen, rptEvtPara}
        STATUS current
        DESCRIPTION
        "Trap of PerEvt: Minimum working temperature of the laser on the channel of the CFP module"
        ::= { optixTrapsPER  15665 }

--  1.3.6.1.4.1.2011.2.25.3.40.40.30.15666
    perEvtCfpLstmpcur NOTIFICATION-TYPE
        OBJECTS { rptEvtPeriod, rptEvtValue, rptEvtVldty, rptEvtDateTime, rptEvtObjType, rptEvtParaLen, rptEvtPara}
        STATUS current
        DESCRIPTION
        "Trap of PerEvt: Current working temperature of the laser on the channel of the CFP module"
        ::= { optixTrapsPER  15666 }

--  1.3.6.1.4.1.2011.2.25.3.40.40.30.15668
    perEvtCfpLsbiasmax NOTIFICATION-TYPE
        OBJECTS { rptEvtPeriod, rptEvtValue, rptEvtVldty, rptEvtDateTime, rptEvtObjType, rptEvtParaLen, rptEvtPara}
        STATUS current
        DESCRIPTION
        "Trap of PerEvt: Maximum bias current of the laser on the channel of the CFP module"
        ::= { optixTrapsPER  15668 }

--  1.3.6.1.4.1.2011.2.25.3.40.40.30.15669
    perEvtCfpLsbiasmin NOTIFICATION-TYPE
        OBJECTS { rptEvtPeriod, rptEvtValue, rptEvtVldty, rptEvtDateTime, rptEvtObjType, rptEvtParaLen, rptEvtPara}
        STATUS current
        DESCRIPTION
        "Trap of PerEvt: Minimum bias current of the laser on the channel of the CFP module"
        ::= { optixTrapsPER  15669 }

--  1.3.6.1.4.1.2011.2.25.3.40.40.30.15670
    perEvtCfpLsbiascur NOTIFICATION-TYPE
        OBJECTS { rptEvtPeriod, rptEvtValue, rptEvtVldty, rptEvtDateTime, rptEvtObjType, rptEvtParaLen, rptEvtPara}
        STATUS current
        DESCRIPTION
        "Trap of PerEvt: Current bias current of the laser on the channel of the CFP module"
        ::= { optixTrapsPER  15670 }

--  1.3.6.1.4.1.2011.2.25.3.40.40.30.5
    perEvtRsofs NOTIFICATION-TYPE
        OBJECTS { rptEvtPeriod, rptEvtValue, rptEvtVldty, rptEvtDateTime, rptEvtObjType, rptEvtParaLen, rptEvtPara}
        STATUS current
        DESCRIPTION
        "Trap of PerEvt: Regenerator section Out-Of-Frame seconds"
        ::= { optixTrapsPER  5 }

--  1.3.6.1.4.1.2011.2.25.3.40.40.30.6
    perEvtRsuas NOTIFICATION-TYPE
        OBJECTS { rptEvtPeriod, rptEvtValue, rptEvtVldty, rptEvtDateTime, rptEvtObjType, rptEvtParaLen, rptEvtPara}
        STATUS current
        DESCRIPTION
        "Trap of PerEvt: Regenerator section unavailable seconds"
        ::= { optixTrapsPER  6 }

--  1.3.6.1.4.1.2011.2.25.3.40.40.30.112
    perEvtWcvmax NOTIFICATION-TYPE
        OBJECTS { rptEvtPeriod, rptEvtValue, rptEvtVldty, rptEvtDateTime, rptEvtObjType, rptEvtParaLen, rptEvtPara}
        STATUS current
        DESCRIPTION
        "Trap of PerEvt: Pump Laser Working Current or Pump Laser Driver Current or Pump Laser Bias Current- the Maximum value"
        ::= { optixTrapsPER  112 }

--  1.3.6.1.4.1.2011.2.25.3.40.40.30.113
    perEvtWcvmin NOTIFICATION-TYPE
        OBJECTS { rptEvtPeriod, rptEvtValue, rptEvtVldty, rptEvtDateTime, rptEvtObjType, rptEvtParaLen, rptEvtPara}
        STATUS current
        DESCRIPTION
        "Trap of PerEvt: Pump Laser Working Current or Pump Laser Driver Current or Pump Laser Bias Current- the Minimum value"
        ::= { optixTrapsPER  113 }

--  1.3.6.1.4.1.2011.2.25.3.40.40.30.114
    perEvtWcvcur NOTIFICATION-TYPE
        OBJECTS { rptEvtPeriod, rptEvtValue, rptEvtVldty, rptEvtDateTime, rptEvtObjType, rptEvtParaLen, rptEvtPara}
        STATUS current
        DESCRIPTION
        "Trap of PerEvt: Pump Laser Working Current or Pump Laser Driver Current or Pump Laser Bias Current- the Current value"
        ::= { optixTrapsPER  114 }

--  1.3.6.1.4.1.2011.2.25.3.40.40.30.115
    perEvtCcvmax NOTIFICATION-TYPE
        OBJECTS { rptEvtPeriod, rptEvtValue, rptEvtVldty, rptEvtDateTime, rptEvtObjType, rptEvtParaLen, rptEvtPara}
        STATUS current
        DESCRIPTION
        "Trap of PerEvt: Pump laser cooling current the maximum value"
        ::= { optixTrapsPER  115 }

--  1.3.6.1.4.1.2011.2.25.3.40.40.30.116
    perEvtCcvmin NOTIFICATION-TYPE
        OBJECTS { rptEvtPeriod, rptEvtValue, rptEvtVldty, rptEvtDateTime, rptEvtObjType, rptEvtParaLen, rptEvtPara}
        STATUS current
        DESCRIPTION
        "Trap of PerEvt: Pump laser cooling current-the minimum value"
        ::= { optixTrapsPER  116 }

--  1.3.6.1.4.1.2011.2.25.3.40.40.30.117
    perEvtCcvcur NOTIFICATION-TYPE
        OBJECTS { rptEvtPeriod, rptEvtValue, rptEvtVldty, rptEvtDateTime, rptEvtObjType, rptEvtParaLen, rptEvtPara}
        STATUS current
        DESCRIPTION
        "Trap of PerEvt: Pump laser cooling current-the current value"
        ::= { optixTrapsPER  117 }

--  1.3.6.1.4.1.2011.2.25.3.40.40.30.130
    perEvtEdtmpmax NOTIFICATION-TYPE
        OBJECTS { rptEvtPeriod, rptEvtValue, rptEvtVldty, rptEvtDateTime, rptEvtObjType, rptEvtParaLen, rptEvtPara}
        STATUS current
        DESCRIPTION
        "Trap of PerEvt: Pump laser temperature-the maximum value "
        ::= { optixTrapsPER  130 }

--  1.3.6.1.4.1.2011.2.25.3.40.40.30.131
    perEvtEdtmpmin NOTIFICATION-TYPE
        OBJECTS { rptEvtPeriod, rptEvtValue, rptEvtVldty, rptEvtDateTime, rptEvtObjType, rptEvtParaLen, rptEvtPara}
        STATUS current
        DESCRIPTION
        "Trap of PerEvt: Pump laser temperature-the minimum value"
        ::= { optixTrapsPER  131 }

--  1.3.6.1.4.1.2011.2.25.3.40.40.30.132
    perEvtEdtmpcur NOTIFICATION-TYPE
        OBJECTS { rptEvtPeriod, rptEvtValue, rptEvtVldty, rptEvtDateTime, rptEvtObjType, rptEvtParaLen, rptEvtPara}
        STATUS current
        DESCRIPTION
        "Trap of PerEvt: Pump laser temperature the current value"
        ::= { optixTrapsPER  132 }

--  1.3.6.1.4.1.2011.2.25.3.40.40.30.213
    perEvtSumoopmax NOTIFICATION-TYPE
        OBJECTS { rptEvtPeriod, rptEvtValue, rptEvtVldty, rptEvtDateTime, rptEvtObjType, rptEvtParaLen, rptEvtPara}
        STATUS current
        DESCRIPTION
        "Trap of PerEvt: Total optical power Transmitted multi wavelengththe maximum value "
        ::= { optixTrapsPER  213 }

--  1.3.6.1.4.1.2011.2.25.3.40.40.30.214
    perEvtSumoopmin NOTIFICATION-TYPE
        OBJECTS { rptEvtPeriod, rptEvtValue, rptEvtVldty, rptEvtDateTime, rptEvtObjType, rptEvtParaLen, rptEvtPara}
        STATUS current
        DESCRIPTION
        "Trap of PerEvt: Total optical power Transmitted multi wavelength the minimum value "
        ::= { optixTrapsPER  214 }

--  1.3.6.1.4.1.2011.2.25.3.40.40.30.215
    perEvtSumoopcur NOTIFICATION-TYPE
        OBJECTS { rptEvtPeriod, rptEvtValue, rptEvtVldty, rptEvtDateTime, rptEvtObjType, rptEvtParaLen, rptEvtPara}
        STATUS current
        DESCRIPTION
        "Trap of PerEvt: Total optical power Transmitted multi wavelength the current value "
        ::= { optixTrapsPER  215 }





--  1.3.6.1.4.1.2011.2.25.3.40.40.30.96
    perEvtTlbmax NOTIFICATION-TYPE
        OBJECTS { rptEvtPeriod, rptEvtValue, rptEvtVldty, rptEvtDateTime, rptEvtObjType, rptEvtParaLen, rptEvtPara}
        STATUS current
        DESCRIPTION
        "Trap of PerEvt: Maximum value of laser transmitting bias current"
        ::= { optixTrapsPER  96 }

--  1.3.6.1.4.1.2011.2.25.3.40.40.30.97
    perEvtTlbmin NOTIFICATION-TYPE
        OBJECTS { rptEvtPeriod, rptEvtValue, rptEvtVldty, rptEvtDateTime, rptEvtObjType, rptEvtParaLen, rptEvtPara}
        STATUS current
        DESCRIPTION
        "Trap of PerEvt: Minimum value of laser transmitting bias current"
        ::= { optixTrapsPER  97 }

--  1.3.6.1.4.1.2011.2.25.3.40.40.30.98
    perEvtTlbcur NOTIFICATION-TYPE
        OBJECTS { rptEvtPeriod, rptEvtValue, rptEvtVldty, rptEvtDateTime, rptEvtObjType, rptEvtParaLen, rptEvtPara}
        STATUS current
        DESCRIPTION
        "Trap of PerEvt: Current value of laser transmitting bias current"
        ::= { optixTrapsPER  98 }

--  1.3.6.1.4.1.2011.2.25.3.40.40.30.99
    perEvtOspiccvmax NOTIFICATION-TYPE
        OBJECTS { rptEvtPeriod, rptEvtValue, rptEvtVldty, rptEvtDateTime, rptEvtObjType, rptEvtParaLen, rptEvtPara}
        STATUS current
        DESCRIPTION
        "Trap of PerEvt: Maximum value of laser cooling Current "
        ::= { optixTrapsPER  99 }

--  1.3.6.1.4.1.2011.2.25.3.40.40.30.100
    perEvtOspiccvmin NOTIFICATION-TYPE
        OBJECTS { rptEvtPeriod, rptEvtValue, rptEvtVldty, rptEvtDateTime, rptEvtObjType, rptEvtParaLen, rptEvtPara}
        STATUS current
        DESCRIPTION
        "Trap of PerEvt: Minimum value of laser cooling Current"
        ::= { optixTrapsPER  100 }

--  1.3.6.1.4.1.2011.2.25.3.40.40.30.101
    perEvtOspiccvcur NOTIFICATION-TYPE
        OBJECTS { rptEvtPeriod, rptEvtValue, rptEvtVldty, rptEvtDateTime, rptEvtObjType, rptEvtParaLen, rptEvtPara}
        STATUS current
        DESCRIPTION
        "Trap of PerEvt: Current value of laser cooling current"
        ::= { optixTrapsPER  101 }

--  1.3.6.1.4.1.2011.2.25.3.40.40.30.102
    perEvtTplmax NOTIFICATION-TYPE
        OBJECTS { rptEvtPeriod, rptEvtValue, rptEvtVldty, rptEvtDateTime, rptEvtObjType, rptEvtParaLen, rptEvtPara}
        STATUS current
        DESCRIPTION
        "Trap of PerEvt: Maximum value of laser transmitting power"
        ::= { optixTrapsPER  102 }

--  1.3.6.1.4.1.2011.2.25.3.40.40.30.103
    perEvtTplmin NOTIFICATION-TYPE
        OBJECTS { rptEvtPeriod, rptEvtValue, rptEvtVldty, rptEvtDateTime, rptEvtObjType, rptEvtParaLen, rptEvtPara}
        STATUS current
        DESCRIPTION
        "Trap of PerEvt: Minimum value of laser transmitting power"
        ::= { optixTrapsPER  103 }

--  1.3.6.1.4.1.2011.2.25.3.40.40.30.104
    perEvtTplcur NOTIFICATION-TYPE
        OBJECTS { rptEvtPeriod, rptEvtValue, rptEvtVldty, rptEvtDateTime, rptEvtObjType, rptEvtParaLen, rptEvtPara}
        STATUS current
        DESCRIPTION
        "Trap of PerEvt: Current value of laser transmitting power"
        ::= { optixTrapsPER  104 }

--  1.3.6.1.4.1.2011.2.25.3.40.40.30.105
    perEvtRplmax NOTIFICATION-TYPE
        OBJECTS { rptEvtPeriod, rptEvtValue, rptEvtVldty, rptEvtDateTime, rptEvtObjType, rptEvtParaLen, rptEvtPara}
        STATUS current
        DESCRIPTION
        "Trap of PerEvt: Maximum value of laser receiving power"
        ::= { optixTrapsPER  105 }

--  1.3.6.1.4.1.2011.2.25.3.40.40.30.106
    perEvtRplmin NOTIFICATION-TYPE
        OBJECTS { rptEvtPeriod, rptEvtValue, rptEvtVldty, rptEvtDateTime, rptEvtObjType, rptEvtParaLen, rptEvtPara}
        STATUS current
        DESCRIPTION
        "Trap of PerEvt: Minimum value of laser receiving power"
        ::= { optixTrapsPER  106 }

--  1.3.6.1.4.1.2011.2.25.3.40.40.30.107
    perEvtRplcur NOTIFICATION-TYPE
        OBJECTS { rptEvtPeriod, rptEvtValue, rptEvtVldty, rptEvtDateTime, rptEvtObjType, rptEvtParaLen, rptEvtPara}
        STATUS current
        DESCRIPTION
        "Trap of PerEvt: Current value of laser receiving power"
        ::= { optixTrapsPER  107 }

--  1.3.6.1.4.1.2011.2.25.3.40.40.30.108
    perEvtOspitmpmax NOTIFICATION-TYPE
        OBJECTS { rptEvtPeriod, rptEvtValue, rptEvtVldty, rptEvtDateTime, rptEvtObjType, rptEvtParaLen, rptEvtPara}
        STATUS current
        DESCRIPTION
        "Trap of PerEvt: Maximum value of laser temperature"
        ::= { optixTrapsPER  108 }

--  1.3.6.1.4.1.2011.2.25.3.40.40.30.109
    perEvtOspitmpmin NOTIFICATION-TYPE
        OBJECTS { rptEvtPeriod, rptEvtValue, rptEvtVldty, rptEvtDateTime, rptEvtObjType, rptEvtParaLen, rptEvtPara}
        STATUS current
        DESCRIPTION
        "Trap of PerEvt: Minimum value of laser temperature"
        ::= { optixTrapsPER  109 }

--  1.3.6.1.4.1.2011.2.25.3.40.40.30.110
    perEvtOspitmpcur NOTIFICATION-TYPE
        OBJECTS { rptEvtPeriod, rptEvtValue, rptEvtVldty, rptEvtDateTime, rptEvtObjType, rptEvtParaLen, rptEvtPara}
        STATUS current
        DESCRIPTION
        "Trap of PerEvt: Current value of laser temperature"
        ::= { optixTrapsPER  110 }




--  1.3.6.1.4.1.2011.2.25.3.40.40.30.222
    perEvtEnvtmpmax NOTIFICATION-TYPE
        OBJECTS { rptEvtPeriod, rptEvtValue, rptEvtVldty, rptEvtDateTime, rptEvtObjType, rptEvtParaLen, rptEvtPara}
        STATUS current
        DESCRIPTION
        "Trap of PerEvt: ENVTMPMAX"
        ::= { optixTrapsPER  222 }

--  1.3.6.1.4.1.2011.2.25.3.40.40.30.223
    perEvtEnvtmpmin NOTIFICATION-TYPE
        OBJECTS { rptEvtPeriod, rptEvtValue, rptEvtVldty, rptEvtDateTime, rptEvtObjType, rptEvtParaLen, rptEvtPara}
        STATUS current
        DESCRIPTION
        "Trap of PerEvt: ENVTMPMIN"
        ::= { optixTrapsPER  223 }

--  1.3.6.1.4.1.2011.2.25.3.40.40.30.224
    perEvtEnvtmpcur NOTIFICATION-TYPE
        OBJECTS { rptEvtPeriod, rptEvtValue, rptEvtVldty, rptEvtDateTime, rptEvtObjType, rptEvtParaLen, rptEvtPara}
        STATUS current
        DESCRIPTION
        "Trap of PerEvt: ENVTMPCUR"
        ::= { optixTrapsPER  224 }

--  1.3.6.1.4.1.2011.2.25.3.40.40.30.14336
    perEvtOtu1Iaes NOTIFICATION-TYPE
        OBJECTS { rptEvtPeriod, rptEvtValue, rptEvtVldty, rptEvtDateTime, rptEvtObjType, rptEvtParaLen, rptEvtPara}
        STATUS current
        DESCRIPTION
        "Trap of PerEvt: OTU1_IAES"
        ::= { optixTrapsPER  14336 }

--  1.3.6.1.4.1.2011.2.25.3.40.40.30.14337
    perEvtOtu1Biaes NOTIFICATION-TYPE
        OBJECTS { rptEvtPeriod, rptEvtValue, rptEvtVldty, rptEvtDateTime, rptEvtObjType, rptEvtParaLen, rptEvtPara}
        STATUS current
        DESCRIPTION
        "Trap of PerEvt: OTU1_BIAES"
        ::= { optixTrapsPER  14337 }

--  1.3.6.1.4.1.2011.2.25.3.40.40.30.14338
    perEvtOtu1Bbe NOTIFICATION-TYPE
        OBJECTS { rptEvtPeriod, rptEvtValue, rptEvtVldty, rptEvtDateTime, rptEvtObjType, rptEvtParaLen, rptEvtPara}
        STATUS current
        DESCRIPTION
        "Trap of PerEvt: OTU1_BBE"
        ::= { optixTrapsPER  14338 }

--  1.3.6.1.4.1.2011.2.25.3.40.40.30.14339
    perEvtOtu1Es NOTIFICATION-TYPE
        OBJECTS { rptEvtPeriod, rptEvtValue, rptEvtVldty, rptEvtDateTime, rptEvtObjType, rptEvtParaLen, rptEvtPara}
        STATUS current
        DESCRIPTION
        "Trap of PerEvt: OTU1_ES"
        ::= { optixTrapsPER  14339 }

--  1.3.6.1.4.1.2011.2.25.3.40.40.30.14340
    perEvtOtu1Ses NOTIFICATION-TYPE
        OBJECTS { rptEvtPeriod, rptEvtValue, rptEvtVldty, rptEvtDateTime, rptEvtObjType, rptEvtParaLen, rptEvtPara}
        STATUS current
        DESCRIPTION
        "Trap of PerEvt: OTU1_SES"
        ::= { optixTrapsPER  14340 }

--  1.3.6.1.4.1.2011.2.25.3.40.40.30.14341
    perEvtOtu1Uas NOTIFICATION-TYPE
        OBJECTS { rptEvtPeriod, rptEvtValue, rptEvtVldty, rptEvtDateTime, rptEvtObjType, rptEvtParaLen, rptEvtPara}
        STATUS current
        DESCRIPTION
        "Trap of PerEvt: OTU1_UAS"
        ::= { optixTrapsPER  14341 }

--  1.3.6.1.4.1.2011.2.25.3.40.40.30.14342
    perEvtOtu1Sesr NOTIFICATION-TYPE
        OBJECTS { rptEvtPeriod, rptEvtValue, rptEvtVldty, rptEvtDateTime, rptEvtObjType, rptEvtParaLen, rptEvtPara}
        STATUS current
        DESCRIPTION
        "Trap of PerEvt: OTU1_SESR"
        ::= { optixTrapsPER  14342 }

--  1.3.6.1.4.1.2011.2.25.3.40.40.30.14343
    perEvtOtu1Bber NOTIFICATION-TYPE
        OBJECTS { rptEvtPeriod, rptEvtValue, rptEvtVldty, rptEvtDateTime, rptEvtObjType, rptEvtParaLen, rptEvtPara}
        STATUS current
        DESCRIPTION
        "Trap of PerEvt: OTU1_BBER"
        ::= { optixTrapsPER  14343 }

--  1.3.6.1.4.1.2011.2.25.3.40.40.30.14344
    perEvtOtu1Febbe NOTIFICATION-TYPE
        OBJECTS { rptEvtPeriod, rptEvtValue, rptEvtVldty, rptEvtDateTime, rptEvtObjType, rptEvtParaLen, rptEvtPara}
        STATUS current
        DESCRIPTION
        "Trap of PerEvt: OTU1_FEBBE"
        ::= { optixTrapsPER  14344 }

--  1.3.6.1.4.1.2011.2.25.3.40.40.30.14345
    perEvtOtu1Fees NOTIFICATION-TYPE
        OBJECTS { rptEvtPeriod, rptEvtValue, rptEvtVldty, rptEvtDateTime, rptEvtObjType, rptEvtParaLen, rptEvtPara}
        STATUS current
        DESCRIPTION
        "Trap of PerEvt: OTU1_FEES"
        ::= { optixTrapsPER  14345 }

--  1.3.6.1.4.1.2011.2.25.3.40.40.30.14346
    perEvtOtu1Feses NOTIFICATION-TYPE
        OBJECTS { rptEvtPeriod, rptEvtValue, rptEvtVldty, rptEvtDateTime, rptEvtObjType, rptEvtParaLen, rptEvtPara}
        STATUS current
        DESCRIPTION
        "Trap of PerEvt: OTU1_FESES"
        ::= { optixTrapsPER  14346 }

--  1.3.6.1.4.1.2011.2.25.3.40.40.30.14347
    perEvtOtu1Feuas NOTIFICATION-TYPE
        OBJECTS { rptEvtPeriod, rptEvtValue, rptEvtVldty, rptEvtDateTime, rptEvtObjType, rptEvtParaLen, rptEvtPara}
        STATUS current
        DESCRIPTION
        "Trap of PerEvt: OTU1_FEUAS"
        ::= { optixTrapsPER  14347 }

--  1.3.6.1.4.1.2011.2.25.3.40.40.30.14348
    perEvtOtu1Fesesr NOTIFICATION-TYPE
        OBJECTS { rptEvtPeriod, rptEvtValue, rptEvtVldty, rptEvtDateTime, rptEvtObjType, rptEvtParaLen, rptEvtPara}
        STATUS current
        DESCRIPTION
        "Trap of PerEvt: OTU1_FESESR"
        ::= { optixTrapsPER  14348 }

--  1.3.6.1.4.1.2011.2.25.3.40.40.30.14349
    perEvtOtu1Febber NOTIFICATION-TYPE
        OBJECTS { rptEvtPeriod, rptEvtValue, rptEvtVldty, rptEvtDateTime, rptEvtObjType, rptEvtParaLen, rptEvtPara}
        STATUS current
        DESCRIPTION
        "Trap of PerEvt: OTU1_FEBBER"
        ::= { optixTrapsPER  14349 }

--  1.3.6.1.4.1.2011.2.25.3.40.40.30.14364
    perEvtOtu2Iaes NOTIFICATION-TYPE
        OBJECTS { rptEvtPeriod, rptEvtValue, rptEvtVldty, rptEvtDateTime, rptEvtObjType, rptEvtParaLen, rptEvtPara}
        STATUS current
        DESCRIPTION
        "Trap of PerEvt: OTU2_IAES"
        ::= { optixTrapsPER  14364 }

--  1.3.6.1.4.1.2011.2.25.3.40.40.30.14365
    perEvtOtu2Biaes NOTIFICATION-TYPE
        OBJECTS { rptEvtPeriod, rptEvtValue, rptEvtVldty, rptEvtDateTime, rptEvtObjType, rptEvtParaLen, rptEvtPara}
        STATUS current
        DESCRIPTION
        "Trap of PerEvt: OTU2_BIAES"
        ::= { optixTrapsPER  14365 }

--  1.3.6.1.4.1.2011.2.25.3.40.40.30.14366
    perEvtOtu2Bbe NOTIFICATION-TYPE
        OBJECTS { rptEvtPeriod, rptEvtValue, rptEvtVldty, rptEvtDateTime, rptEvtObjType, rptEvtParaLen, rptEvtPara}
        STATUS current
        DESCRIPTION
        "Trap of PerEvt: OTU2_BBE"
        ::= { optixTrapsPER  14366 }

--  1.3.6.1.4.1.2011.2.25.3.40.40.30.14367
    perEvtOtu2Es NOTIFICATION-TYPE
        OBJECTS { rptEvtPeriod, rptEvtValue, rptEvtVldty, rptEvtDateTime, rptEvtObjType, rptEvtParaLen, rptEvtPara}
        STATUS current
        DESCRIPTION
        "Trap of PerEvt: OTU2_ES"
        ::= { optixTrapsPER  14367 }

--  1.3.6.1.4.1.2011.2.25.3.40.40.30.14368
    perEvtOtu2Ses NOTIFICATION-TYPE
        OBJECTS { rptEvtPeriod, rptEvtValue, rptEvtVldty, rptEvtDateTime, rptEvtObjType, rptEvtParaLen, rptEvtPara}
        STATUS current
        DESCRIPTION
        "Trap of PerEvt: OTU2_SES"
        ::= { optixTrapsPER  14368 }

--  1.3.6.1.4.1.2011.2.25.3.40.40.30.14369
    perEvtOtu2Uas NOTIFICATION-TYPE
        OBJECTS { rptEvtPeriod, rptEvtValue, rptEvtVldty, rptEvtDateTime, rptEvtObjType, rptEvtParaLen, rptEvtPara}
        STATUS current
        DESCRIPTION
        "Trap of PerEvt: OTU2_UAS"
        ::= { optixTrapsPER  14369 }

--  1.3.6.1.4.1.2011.2.25.3.40.40.30.14370
    perEvtOtu2Sesr NOTIFICATION-TYPE
        OBJECTS { rptEvtPeriod, rptEvtValue, rptEvtVldty, rptEvtDateTime, rptEvtObjType, rptEvtParaLen, rptEvtPara}
        STATUS current
        DESCRIPTION
        "Trap of PerEvt: OTU2_SESR"
        ::= { optixTrapsPER  14370 }

--  1.3.6.1.4.1.2011.2.25.3.40.40.30.14371
    perEvtOtu2Bber NOTIFICATION-TYPE
        OBJECTS { rptEvtPeriod, rptEvtValue, rptEvtVldty, rptEvtDateTime, rptEvtObjType, rptEvtParaLen, rptEvtPara}
        STATUS current
        DESCRIPTION
        "Trap of PerEvt: OTU2_BBER"
        ::= { optixTrapsPER  14371 }

--  1.3.6.1.4.1.2011.2.25.3.40.40.30.14372
    perEvtOtu2Febbe NOTIFICATION-TYPE
        OBJECTS { rptEvtPeriod, rptEvtValue, rptEvtVldty, rptEvtDateTime, rptEvtObjType, rptEvtParaLen, rptEvtPara}
        STATUS current
        DESCRIPTION
        "Trap of PerEvt: OTU2_FEBBE"
        ::= { optixTrapsPER  14372 }

--  1.3.6.1.4.1.2011.2.25.3.40.40.30.14373
    perEvtOtu2Fees NOTIFICATION-TYPE
        OBJECTS { rptEvtPeriod, rptEvtValue, rptEvtVldty, rptEvtDateTime, rptEvtObjType, rptEvtParaLen, rptEvtPara}
        STATUS current
        DESCRIPTION
        "Trap of PerEvt: OTU2_FEES"
        ::= { optixTrapsPER  14373 }

--  1.3.6.1.4.1.2011.2.25.3.40.40.30.14374
    perEvtOtu2Feses NOTIFICATION-TYPE
        OBJECTS { rptEvtPeriod, rptEvtValue, rptEvtVldty, rptEvtDateTime, rptEvtObjType, rptEvtParaLen, rptEvtPara}
        STATUS current
        DESCRIPTION
        "Trap of PerEvt: OTU2_FESES"
        ::= { optixTrapsPER  14374 }

--  1.3.6.1.4.1.2011.2.25.3.40.40.30.14375
    perEvtOtu2Feuas NOTIFICATION-TYPE
        OBJECTS { rptEvtPeriod, rptEvtValue, rptEvtVldty, rptEvtDateTime, rptEvtObjType, rptEvtParaLen, rptEvtPara}
        STATUS current
        DESCRIPTION
        "Trap of PerEvt: OTU2_FEUAS"
        ::= { optixTrapsPER  14375 }

--  1.3.6.1.4.1.2011.2.25.3.40.40.30.14376
    perEvtOtu2Fesesr NOTIFICATION-TYPE
        OBJECTS { rptEvtPeriod, rptEvtValue, rptEvtVldty, rptEvtDateTime, rptEvtObjType, rptEvtParaLen, rptEvtPara}
        STATUS current
        DESCRIPTION
        "Trap of PerEvt: OTU2_FESESR"
        ::= { optixTrapsPER  14376 }

--  1.3.6.1.4.1.2011.2.25.3.40.40.30.14377
    perEvtOtu2Febber NOTIFICATION-TYPE
        OBJECTS { rptEvtPeriod, rptEvtValue, rptEvtVldty, rptEvtDateTime, rptEvtObjType, rptEvtParaLen, rptEvtPara}
        STATUS current
        DESCRIPTION
        "Trap of PerEvt: OTU2_FEBBER"
        ::= { optixTrapsPER  14377 }

--  1.3.6.1.4.1.2011.2.25.3.40.40.30.14378
    perEvtOtu3Iaes NOTIFICATION-TYPE
        OBJECTS { rptEvtPeriod, rptEvtValue, rptEvtVldty, rptEvtDateTime, rptEvtObjType, rptEvtParaLen, rptEvtPara}
        STATUS current
        DESCRIPTION
        "Trap of PerEvt: OTU3_IAES"
        ::= { optixTrapsPER  14378 }

--  1.3.6.1.4.1.2011.2.25.3.40.40.30.14379
    perEvtOtu3Biaes NOTIFICATION-TYPE
        OBJECTS { rptEvtPeriod, rptEvtValue, rptEvtVldty, rptEvtDateTime, rptEvtObjType, rptEvtParaLen, rptEvtPara}
        STATUS current
        DESCRIPTION
        "Trap of PerEvt: OTU3_BIAES"
        ::= { optixTrapsPER  14379 }

--  1.3.6.1.4.1.2011.2.25.3.40.40.30.14380
    perEvtOtu3Bbe NOTIFICATION-TYPE
        OBJECTS { rptEvtPeriod, rptEvtValue, rptEvtVldty, rptEvtDateTime, rptEvtObjType, rptEvtParaLen, rptEvtPara}
        STATUS current
        DESCRIPTION
        "Trap of PerEvt: OTU3_BBE"
        ::= { optixTrapsPER  14380 }

--  1.3.6.1.4.1.2011.2.25.3.40.40.30.14381
    perEvtOtu3Es NOTIFICATION-TYPE
        OBJECTS { rptEvtPeriod, rptEvtValue, rptEvtVldty, rptEvtDateTime, rptEvtObjType, rptEvtParaLen, rptEvtPara}
        STATUS current
        DESCRIPTION
        "Trap of PerEvt: OTU3_ES"
        ::= { optixTrapsPER  14381 }

--  1.3.6.1.4.1.2011.2.25.3.40.40.30.14382
    perEvtOtu3Ses NOTIFICATION-TYPE
        OBJECTS { rptEvtPeriod, rptEvtValue, rptEvtVldty, rptEvtDateTime, rptEvtObjType, rptEvtParaLen, rptEvtPara}
        STATUS current
        DESCRIPTION
        "Trap of PerEvt: OTU3_SES"
        ::= { optixTrapsPER  14382 }

--  1.3.6.1.4.1.2011.2.25.3.40.40.30.14383
    perEvtOtu3Uas NOTIFICATION-TYPE
        OBJECTS { rptEvtPeriod, rptEvtValue, rptEvtVldty, rptEvtDateTime, rptEvtObjType, rptEvtParaLen, rptEvtPara}
        STATUS current
        DESCRIPTION
        "Trap of PerEvt: OTU3_UAS"
        ::= { optixTrapsPER  14383 }

--  1.3.6.1.4.1.2011.2.25.3.40.40.30.14384
    perEvtOtu3Sesr NOTIFICATION-TYPE
        OBJECTS { rptEvtPeriod, rptEvtValue, rptEvtVldty, rptEvtDateTime, rptEvtObjType, rptEvtParaLen, rptEvtPara}
        STATUS current
        DESCRIPTION
        "Trap of PerEvt: OTU3_SESR"
        ::= { optixTrapsPER  14384 }

--  1.3.6.1.4.1.2011.2.25.3.40.40.30.14385
    perEvtOtu3Bber NOTIFICATION-TYPE
        OBJECTS { rptEvtPeriod, rptEvtValue, rptEvtVldty, rptEvtDateTime, rptEvtObjType, rptEvtParaLen, rptEvtPara}
        STATUS current
        DESCRIPTION
        "Trap of PerEvt: OTU3_BBER"
        ::= { optixTrapsPER  14385 }

--  1.3.6.1.4.1.2011.2.25.3.40.40.30.14386
    perEvtOtu3Febbe NOTIFICATION-TYPE
        OBJECTS { rptEvtPeriod, rptEvtValue, rptEvtVldty, rptEvtDateTime, rptEvtObjType, rptEvtParaLen, rptEvtPara}
        STATUS current
        DESCRIPTION
        "Trap of PerEvt: OTU3_FEBBE"
        ::= { optixTrapsPER  14386 }

--  1.3.6.1.4.1.2011.2.25.3.40.40.30.14387
    perEvtOtu3Fees NOTIFICATION-TYPE
        OBJECTS { rptEvtPeriod, rptEvtValue, rptEvtVldty, rptEvtDateTime, rptEvtObjType, rptEvtParaLen, rptEvtPara}
        STATUS current
        DESCRIPTION
        "Trap of PerEvt: OTU3_FEES"
        ::= { optixTrapsPER  14387 }

--  1.3.6.1.4.1.2011.2.25.3.40.40.30.14388
    perEvtOtu3Feses NOTIFICATION-TYPE
        OBJECTS { rptEvtPeriod, rptEvtValue, rptEvtVldty, rptEvtDateTime, rptEvtObjType, rptEvtParaLen, rptEvtPara}
        STATUS current
        DESCRIPTION
        "Trap of PerEvt: OTU3_FESES"
        ::= { optixTrapsPER  14388 }

--  1.3.6.1.4.1.2011.2.25.3.40.40.30.14389
    perEvtOtu3Feuas NOTIFICATION-TYPE
        OBJECTS { rptEvtPeriod, rptEvtValue, rptEvtVldty, rptEvtDateTime, rptEvtObjType, rptEvtParaLen, rptEvtPara}
        STATUS current
        DESCRIPTION
        "Trap of PerEvt: OTU3_FEUAS"
        ::= { optixTrapsPER  14389 }

--  1.3.6.1.4.1.2011.2.25.3.40.40.30.14390
    perEvtOtu3Fesesr NOTIFICATION-TYPE
        OBJECTS { rptEvtPeriod, rptEvtValue, rptEvtVldty, rptEvtDateTime, rptEvtObjType, rptEvtParaLen, rptEvtPara}
        STATUS current
        DESCRIPTION
        "Trap of PerEvt: OTU3_FESESR"
        ::= { optixTrapsPER  14390 }

--  1.3.6.1.4.1.2011.2.25.3.40.40.30.14391
    perEvtOtu3Febber NOTIFICATION-TYPE
        OBJECTS { rptEvtPeriod, rptEvtValue, rptEvtVldty, rptEvtDateTime, rptEvtObjType, rptEvtParaLen, rptEvtPara}
        STATUS current
        DESCRIPTION
        "Trap of PerEvt: OTU3_FEBBER"
        ::= { optixTrapsPER  14391 }

--  1.3.6.1.4.1.2011.2.25.3.40.40.30.14392
    perEvtOdu1PmBbe NOTIFICATION-TYPE
        OBJECTS { rptEvtPeriod, rptEvtValue, rptEvtVldty, rptEvtDateTime, rptEvtObjType, rptEvtParaLen, rptEvtPara}
        STATUS current
        DESCRIPTION
        "Trap of PerEvt: ODU1_PM_BBE"
        ::= { optixTrapsPER  14392 }

--  1.3.6.1.4.1.2011.2.25.3.40.40.30.14393
    perEvtOdu1PmEs NOTIFICATION-TYPE
        OBJECTS { rptEvtPeriod, rptEvtValue, rptEvtVldty, rptEvtDateTime, rptEvtObjType, rptEvtParaLen, rptEvtPara}
        STATUS current
        DESCRIPTION
        "Trap of PerEvt: ODU1_PM_ES"
        ::= { optixTrapsPER  14393 }

--  1.3.6.1.4.1.2011.2.25.3.40.40.30.14394
    perEvtOdu1PmSes NOTIFICATION-TYPE
        OBJECTS { rptEvtPeriod, rptEvtValue, rptEvtVldty, rptEvtDateTime, rptEvtObjType, rptEvtParaLen, rptEvtPara}
        STATUS current
        DESCRIPTION
        "Trap of PerEvt: ODU1_PM_SES"
        ::= { optixTrapsPER  14394 }

--  1.3.6.1.4.1.2011.2.25.3.40.40.30.14395
    perEvtOdu1PmUas NOTIFICATION-TYPE
        OBJECTS { rptEvtPeriod, rptEvtValue, rptEvtVldty, rptEvtDateTime, rptEvtObjType, rptEvtParaLen, rptEvtPara}
        STATUS current
        DESCRIPTION
        "Trap of PerEvt: ODU1_PM_UAS"
        ::= { optixTrapsPER  14395 }

--  1.3.6.1.4.1.2011.2.25.3.40.40.30.14396
    perEvtOdu1PmSesr NOTIFICATION-TYPE
        OBJECTS { rptEvtPeriod, rptEvtValue, rptEvtVldty, rptEvtDateTime, rptEvtObjType, rptEvtParaLen, rptEvtPara}
        STATUS current
        DESCRIPTION
        "Trap of PerEvt: ODU1_PM_SESR"
        ::= { optixTrapsPER  14396 }

--  1.3.6.1.4.1.2011.2.25.3.40.40.30.14397
    perEvtOdu1PmBber NOTIFICATION-TYPE
        OBJECTS { rptEvtPeriod, rptEvtValue, rptEvtVldty, rptEvtDateTime, rptEvtObjType, rptEvtParaLen, rptEvtPara}
        STATUS current
        DESCRIPTION
        "Trap of PerEvt: ODU1_PM_BBER"
        ::= { optixTrapsPER  14397 }

--  1.3.6.1.4.1.2011.2.25.3.40.40.30.14398
    perEvtOdu1PmFebbe NOTIFICATION-TYPE
        OBJECTS { rptEvtPeriod, rptEvtValue, rptEvtVldty, rptEvtDateTime, rptEvtObjType, rptEvtParaLen, rptEvtPara}
        STATUS current
        DESCRIPTION
        "Trap of PerEvt: ODU1_PM_FEBBE"
        ::= { optixTrapsPER  14398 }

--  1.3.6.1.4.1.2011.2.25.3.40.40.30.14399
    perEvtOdu1PmFees NOTIFICATION-TYPE
        OBJECTS { rptEvtPeriod, rptEvtValue, rptEvtVldty, rptEvtDateTime, rptEvtObjType, rptEvtParaLen, rptEvtPara}
        STATUS current
        DESCRIPTION
        "Trap of PerEvt: ODU1_PM_FEES"
        ::= { optixTrapsPER  14399 }

--  1.3.6.1.4.1.2011.2.25.3.40.40.30.14400
    perEvtOdu1PmFeses NOTIFICATION-TYPE
        OBJECTS { rptEvtPeriod, rptEvtValue, rptEvtVldty, rptEvtDateTime, rptEvtObjType, rptEvtParaLen, rptEvtPara}
        STATUS current
        DESCRIPTION
        "Trap of PerEvt: ODU1_PM_FESES"
        ::= { optixTrapsPER  14400 }

--  1.3.6.1.4.1.2011.2.25.3.40.40.30.14401
    perEvtOdu1PmFeuas NOTIFICATION-TYPE
        OBJECTS { rptEvtPeriod, rptEvtValue, rptEvtVldty, rptEvtDateTime, rptEvtObjType, rptEvtParaLen, rptEvtPara}
        STATUS current
        DESCRIPTION
        "Trap of PerEvt: ODU1_PM_FEUAS"
        ::= { optixTrapsPER  14401 }

--  1.3.6.1.4.1.2011.2.25.3.40.40.30.14402
    perEvtOdu1PmFesesr NOTIFICATION-TYPE
        OBJECTS { rptEvtPeriod, rptEvtValue, rptEvtVldty, rptEvtDateTime, rptEvtObjType, rptEvtParaLen, rptEvtPara}
        STATUS current
        DESCRIPTION
        "Trap of PerEvt: ODU1_PM_FESESR"
        ::= { optixTrapsPER  14402 }

--  1.3.6.1.4.1.2011.2.25.3.40.40.30.14403
    perEvtOdu1PmFebber NOTIFICATION-TYPE
        OBJECTS { rptEvtPeriod, rptEvtValue, rptEvtVldty, rptEvtDateTime, rptEvtObjType, rptEvtParaLen, rptEvtPara}
        STATUS current
        DESCRIPTION
        "Trap of PerEvt: ODU1_PM_FEBBER"
        ::= { optixTrapsPER  14403 }

--  1.3.6.1.4.1.2011.2.25.3.40.40.30.14440
    perEvtOdu1Tcm1Iaes NOTIFICATION-TYPE
        OBJECTS { rptEvtPeriod, rptEvtValue, rptEvtVldty, rptEvtDateTime, rptEvtObjType, rptEvtParaLen, rptEvtPara}
        STATUS current
        DESCRIPTION
        "Trap of PerEvt: ODU1_TCM1_IAES"
        ::= { optixTrapsPER  14440 }

--  1.3.6.1.4.1.2011.2.25.3.40.40.30.14441
    perEvtOdu1Tcm2Iaes NOTIFICATION-TYPE
        OBJECTS { rptEvtPeriod, rptEvtValue, rptEvtVldty, rptEvtDateTime, rptEvtObjType, rptEvtParaLen, rptEvtPara}
        STATUS current
        DESCRIPTION
        "Trap of PerEvt: ODU1_TCM2_IAES"
        ::= { optixTrapsPER  14441 }

--  1.3.6.1.4.1.2011.2.25.3.40.40.30.14442
    perEvtOdu1Tcm3Iaes NOTIFICATION-TYPE
        OBJECTS { rptEvtPeriod, rptEvtValue, rptEvtVldty, rptEvtDateTime, rptEvtObjType, rptEvtParaLen, rptEvtPara}
        STATUS current
        DESCRIPTION
        "Trap of PerEvt: ODU1_TCM3_IAES"
        ::= { optixTrapsPER  14442 }

--  1.3.6.1.4.1.2011.2.25.3.40.40.30.14443
    perEvtOdu1Tcm4Iaes NOTIFICATION-TYPE
        OBJECTS { rptEvtPeriod, rptEvtValue, rptEvtVldty, rptEvtDateTime, rptEvtObjType, rptEvtParaLen, rptEvtPara}
        STATUS current
        DESCRIPTION
        "Trap of PerEvt: ODU1_TCM4_IAES"
        ::= { optixTrapsPER  14443 }

--  1.3.6.1.4.1.2011.2.25.3.40.40.30.14444
    perEvtOdu1Tcm5Iaes NOTIFICATION-TYPE
        OBJECTS { rptEvtPeriod, rptEvtValue, rptEvtVldty, rptEvtDateTime, rptEvtObjType, rptEvtParaLen, rptEvtPara}
        STATUS current
        DESCRIPTION
        "Trap of PerEvt: ODU1_TCM5_IAES"
        ::= { optixTrapsPER  14444 }

--  1.3.6.1.4.1.2011.2.25.3.40.40.30.14445
    perEvtOdu1Tcm6Iaes NOTIFICATION-TYPE
        OBJECTS { rptEvtPeriod, rptEvtValue, rptEvtVldty, rptEvtDateTime, rptEvtObjType, rptEvtParaLen, rptEvtPara}
        STATUS current
        DESCRIPTION
        "Trap of PerEvt: ODU1_TCM6_IAES"
        ::= { optixTrapsPER  14445 }

--  1.3.6.1.4.1.2011.2.25.3.40.40.30.14446
    perEvtOdu1Tcm1Biaes NOTIFICATION-TYPE
        OBJECTS { rptEvtPeriod, rptEvtValue, rptEvtVldty, rptEvtDateTime, rptEvtObjType, rptEvtParaLen, rptEvtPara}
        STATUS current
        DESCRIPTION
        "Trap of PerEvt: ODU1_TCM1_BIAES"
        ::= { optixTrapsPER  14446 }

--  1.3.6.1.4.1.2011.2.25.3.40.40.30.14447
    perEvtOdu1Tcm2Biaes NOTIFICATION-TYPE
        OBJECTS { rptEvtPeriod, rptEvtValue, rptEvtVldty, rptEvtDateTime, rptEvtObjType, rptEvtParaLen, rptEvtPara}
        STATUS current
        DESCRIPTION
        "Trap of PerEvt: ODU1_TCM2_BIAES"
        ::= { optixTrapsPER  14447 }

--  1.3.6.1.4.1.2011.2.25.3.40.40.30.14448
    perEvtOdu1Tcm3Biaes NOTIFICATION-TYPE
        OBJECTS { rptEvtPeriod, rptEvtValue, rptEvtVldty, rptEvtDateTime, rptEvtObjType, rptEvtParaLen, rptEvtPara}
        STATUS current
        DESCRIPTION
        "Trap of PerEvt: ODU1_TCM3_BIAES"
        ::= { optixTrapsPER  14448 }

--  1.3.6.1.4.1.2011.2.25.3.40.40.30.14449
    perEvtOdu1Tcm4Biaes NOTIFICATION-TYPE
        OBJECTS { rptEvtPeriod, rptEvtValue, rptEvtVldty, rptEvtDateTime, rptEvtObjType, rptEvtParaLen, rptEvtPara}
        STATUS current
        DESCRIPTION
        "Trap of PerEvt: ODU1_TCM4_BIAES"
        ::= { optixTrapsPER  14449 }

--  1.3.6.1.4.1.2011.2.25.3.40.40.30.14450
    perEvtOdu1Tcm5Biaes NOTIFICATION-TYPE
        OBJECTS { rptEvtPeriod, rptEvtValue, rptEvtVldty, rptEvtDateTime, rptEvtObjType, rptEvtParaLen, rptEvtPara}
        STATUS current
        DESCRIPTION
        "Trap of PerEvt: ODU1_TCM5_BIAES"
        ::= { optixTrapsPER  14450 }

--  1.3.6.1.4.1.2011.2.25.3.40.40.30.14451
    perEvtOdu1Tcm6Biaes NOTIFICATION-TYPE
        OBJECTS { rptEvtPeriod, rptEvtValue, rptEvtVldty, rptEvtDateTime, rptEvtObjType, rptEvtParaLen, rptEvtPara}
        STATUS current
        DESCRIPTION
        "Trap of PerEvt: ODU1_TCM6_BIAES"
        ::= { optixTrapsPER  14451 }

--  1.3.6.1.4.1.2011.2.25.3.40.40.30.14452
    perEvtOdu1Tcm1Bbe NOTIFICATION-TYPE
        OBJECTS { rptEvtPeriod, rptEvtValue, rptEvtVldty, rptEvtDateTime, rptEvtObjType, rptEvtParaLen, rptEvtPara}
        STATUS current
        DESCRIPTION
        "Trap of PerEvt: ODU1_TCM1_BBE"
        ::= { optixTrapsPER  14452 }

--  1.3.6.1.4.1.2011.2.25.3.40.40.30.14453
    perEvtOdu1Tcm1Es NOTIFICATION-TYPE
        OBJECTS { rptEvtPeriod, rptEvtValue, rptEvtVldty, rptEvtDateTime, rptEvtObjType, rptEvtParaLen, rptEvtPara}
        STATUS current
        DESCRIPTION
        "Trap of PerEvt: ODU1_TCM1_ES"
        ::= { optixTrapsPER  14453 }

--  1.3.6.1.4.1.2011.2.25.3.40.40.30.14454
    perEvtOdu1Tcm1Ses NOTIFICATION-TYPE
        OBJECTS { rptEvtPeriod, rptEvtValue, rptEvtVldty, rptEvtDateTime, rptEvtObjType, rptEvtParaLen, rptEvtPara}
        STATUS current
        DESCRIPTION
        "Trap of PerEvt: ODU1_TCM1_SES"
        ::= { optixTrapsPER  14454 }

--  1.3.6.1.4.1.2011.2.25.3.40.40.30.14455
    perEvtOdu1Tcm1Uas NOTIFICATION-TYPE
        OBJECTS { rptEvtPeriod, rptEvtValue, rptEvtVldty, rptEvtDateTime, rptEvtObjType, rptEvtParaLen, rptEvtPara}
        STATUS current
        DESCRIPTION
        "Trap of PerEvt: ODU1_TCM1_UAS"
        ::= { optixTrapsPER  14455 }

--  1.3.6.1.4.1.2011.2.25.3.40.40.30.14456
    perEvtOdu1Tcm1Sesr NOTIFICATION-TYPE
        OBJECTS { rptEvtPeriod, rptEvtValue, rptEvtVldty, rptEvtDateTime, rptEvtObjType, rptEvtParaLen, rptEvtPara}
        STATUS current
        DESCRIPTION
        "Trap of PerEvt: ODU1_TCM1_SESR"
        ::= { optixTrapsPER  14456 }

--  1.3.6.1.4.1.2011.2.25.3.40.40.30.14457
    perEvtOdu1Tcm1Bber NOTIFICATION-TYPE
        OBJECTS { rptEvtPeriod, rptEvtValue, rptEvtVldty, rptEvtDateTime, rptEvtObjType, rptEvtParaLen, rptEvtPara}
        STATUS current
        DESCRIPTION
        "Trap of PerEvt: ODU1_TCM1_BBER"
        ::= { optixTrapsPER  14457 }

--  1.3.6.1.4.1.2011.2.25.3.40.40.30.14458
    perEvtOdu1Tcm2Bbe NOTIFICATION-TYPE
        OBJECTS { rptEvtPeriod, rptEvtValue, rptEvtVldty, rptEvtDateTime, rptEvtObjType, rptEvtParaLen, rptEvtPara}
        STATUS current
        DESCRIPTION
        "Trap of PerEvt: ODU1_TCM2_BBE"
        ::= { optixTrapsPER  14458 }

--  1.3.6.1.4.1.2011.2.25.3.40.40.30.14459
    perEvtOdu1Tcm2Es NOTIFICATION-TYPE
        OBJECTS { rptEvtPeriod, rptEvtValue, rptEvtVldty, rptEvtDateTime, rptEvtObjType, rptEvtParaLen, rptEvtPara}
        STATUS current
        DESCRIPTION
        "Trap of PerEvt: ODU1_TCM2_ES"
        ::= { optixTrapsPER  14459 }

--  1.3.6.1.4.1.2011.2.25.3.40.40.30.14460
    perEvtOdu1Tcm2Ses NOTIFICATION-TYPE
        OBJECTS { rptEvtPeriod, rptEvtValue, rptEvtVldty, rptEvtDateTime, rptEvtObjType, rptEvtParaLen, rptEvtPara}
        STATUS current
        DESCRIPTION
        "Trap of PerEvt: ODU1_TCM2_SES"
        ::= { optixTrapsPER  14460 }

--  1.3.6.1.4.1.2011.2.25.3.40.40.30.14461
    perEvtOdu1Tcm2Uas NOTIFICATION-TYPE
        OBJECTS { rptEvtPeriod, rptEvtValue, rptEvtVldty, rptEvtDateTime, rptEvtObjType, rptEvtParaLen, rptEvtPara}
        STATUS current
        DESCRIPTION
        "Trap of PerEvt: ODU1_TCM2_UAS"
        ::= { optixTrapsPER  14461 }

--  1.3.6.1.4.1.2011.2.25.3.40.40.30.14462
    perEvtOdu1Tcm2Sesr NOTIFICATION-TYPE
        OBJECTS { rptEvtPeriod, rptEvtValue, rptEvtVldty, rptEvtDateTime, rptEvtObjType, rptEvtParaLen, rptEvtPara}
        STATUS current
        DESCRIPTION
        "Trap of PerEvt: ODU1_TCM2_SESR"
        ::= { optixTrapsPER  14462 }

--  1.3.6.1.4.1.2011.2.25.3.40.40.30.14463
    perEvtOdu1Tcm2Bber NOTIFICATION-TYPE
        OBJECTS { rptEvtPeriod, rptEvtValue, rptEvtVldty, rptEvtDateTime, rptEvtObjType, rptEvtParaLen, rptEvtPara}
        STATUS current
        DESCRIPTION
        "Trap of PerEvt: ODU1_TCM2_BBER"
        ::= { optixTrapsPER  14463 }

--  1.3.6.1.4.1.2011.2.25.3.40.40.30.14464
    perEvtOdu1Tcm3Bbe NOTIFICATION-TYPE
        OBJECTS { rptEvtPeriod, rptEvtValue, rptEvtVldty, rptEvtDateTime, rptEvtObjType, rptEvtParaLen, rptEvtPara}
        STATUS current
        DESCRIPTION
        "Trap of PerEvt: ODU1_TCM3_BBE"
        ::= { optixTrapsPER  14464 }

--  1.3.6.1.4.1.2011.2.25.3.40.40.30.14465
    perEvtOdu1Tcm3Es NOTIFICATION-TYPE
        OBJECTS { rptEvtPeriod, rptEvtValue, rptEvtVldty, rptEvtDateTime, rptEvtObjType, rptEvtParaLen, rptEvtPara}
        STATUS current
        DESCRIPTION
        "Trap of PerEvt: ODU1_TCM3_ES"
        ::= { optixTrapsPER  14465 }

--  1.3.6.1.4.1.2011.2.25.3.40.40.30.14466
    perEvtOdu1Tcm3Ses NOTIFICATION-TYPE
        OBJECTS { rptEvtPeriod, rptEvtValue, rptEvtVldty, rptEvtDateTime, rptEvtObjType, rptEvtParaLen, rptEvtPara}
        STATUS current
        DESCRIPTION
        "Trap of PerEvt: ODU1_TCM3_SES"
        ::= { optixTrapsPER  14466 }

--  1.3.6.1.4.1.2011.2.25.3.40.40.30.14467
    perEvtOdu1Tcm3Uas NOTIFICATION-TYPE
        OBJECTS { rptEvtPeriod, rptEvtValue, rptEvtVldty, rptEvtDateTime, rptEvtObjType, rptEvtParaLen, rptEvtPara}
        STATUS current
        DESCRIPTION
        "Trap of PerEvt: ODU1_TCM3_UAS"
        ::= { optixTrapsPER  14467 }

--  1.3.6.1.4.1.2011.2.25.3.40.40.30.14468
    perEvtOdu1Tcm3Sesr NOTIFICATION-TYPE
        OBJECTS { rptEvtPeriod, rptEvtValue, rptEvtVldty, rptEvtDateTime, rptEvtObjType, rptEvtParaLen, rptEvtPara}
        STATUS current
        DESCRIPTION
        "Trap of PerEvt: ODU1_TCM3_SESR"
        ::= { optixTrapsPER  14468 }

--  1.3.6.1.4.1.2011.2.25.3.40.40.30.14469
    perEvtOdu1Tcm3Bber NOTIFICATION-TYPE
        OBJECTS { rptEvtPeriod, rptEvtValue, rptEvtVldty, rptEvtDateTime, rptEvtObjType, rptEvtParaLen, rptEvtPara}
        STATUS current
        DESCRIPTION
        "Trap of PerEvt: ODU1_TCM3_BBER"
        ::= { optixTrapsPER  14469 }

--  1.3.6.1.4.1.2011.2.25.3.40.40.30.14470
    perEvtOdu1Tcm4Bbe NOTIFICATION-TYPE
        OBJECTS { rptEvtPeriod, rptEvtValue, rptEvtVldty, rptEvtDateTime, rptEvtObjType, rptEvtParaLen, rptEvtPara}
        STATUS current
        DESCRIPTION
        "Trap of PerEvt: ODU1_TCM4_BBE"
        ::= { optixTrapsPER  14470 }

--  1.3.6.1.4.1.2011.2.25.3.40.40.30.14471
    perEvtOdu1Tcm4Es NOTIFICATION-TYPE
        OBJECTS { rptEvtPeriod, rptEvtValue, rptEvtVldty, rptEvtDateTime, rptEvtObjType, rptEvtParaLen, rptEvtPara}
        STATUS current
        DESCRIPTION
        "Trap of PerEvt: ODU1_TCM4_ES"
        ::= { optixTrapsPER  14471 }

--  1.3.6.1.4.1.2011.2.25.3.40.40.30.14472
    perEvtOdu1Tcm4Ses NOTIFICATION-TYPE
        OBJECTS { rptEvtPeriod, rptEvtValue, rptEvtVldty, rptEvtDateTime, rptEvtObjType, rptEvtParaLen, rptEvtPara}
        STATUS current
        DESCRIPTION
        "Trap of PerEvt: ODU1_TCM4_SES"
        ::= { optixTrapsPER  14472 }

--  1.3.6.1.4.1.2011.2.25.3.40.40.30.14473
    perEvtOdu1Tcm4Uas NOTIFICATION-TYPE
        OBJECTS { rptEvtPeriod, rptEvtValue, rptEvtVldty, rptEvtDateTime, rptEvtObjType, rptEvtParaLen, rptEvtPara}
        STATUS current
        DESCRIPTION
        "Trap of PerEvt: ODU1_TCM4_UAS"
        ::= { optixTrapsPER  14473 }

--  1.3.6.1.4.1.2011.2.25.3.40.40.30.14474
    perEvtOdu1Tcm4Sesr NOTIFICATION-TYPE
        OBJECTS { rptEvtPeriod, rptEvtValue, rptEvtVldty, rptEvtDateTime, rptEvtObjType, rptEvtParaLen, rptEvtPara}
        STATUS current
        DESCRIPTION
        "Trap of PerEvt: ODU1_TCM4_SESR"
        ::= { optixTrapsPER  14474 }

--  1.3.6.1.4.1.2011.2.25.3.40.40.30.14475
    perEvtOdu1Tcm4Bber NOTIFICATION-TYPE
        OBJECTS { rptEvtPeriod, rptEvtValue, rptEvtVldty, rptEvtDateTime, rptEvtObjType, rptEvtParaLen, rptEvtPara}
        STATUS current
        DESCRIPTION
        "Trap of PerEvt: ODU1_TCM4_BBER"
        ::= { optixTrapsPER  14475 }

--  1.3.6.1.4.1.2011.2.25.3.40.40.30.14476
    perEvtOdu1Tcm5Bbe NOTIFICATION-TYPE
        OBJECTS { rptEvtPeriod, rptEvtValue, rptEvtVldty, rptEvtDateTime, rptEvtObjType, rptEvtParaLen, rptEvtPara}
        STATUS current
        DESCRIPTION
        "Trap of PerEvt: ODU1_TCM5_BBE"
        ::= { optixTrapsPER  14476 }

--  1.3.6.1.4.1.2011.2.25.3.40.40.30.14477
    perEvtOdu1Tcm5Es NOTIFICATION-TYPE
        OBJECTS { rptEvtPeriod, rptEvtValue, rptEvtVldty, rptEvtDateTime, rptEvtObjType, rptEvtParaLen, rptEvtPara}
        STATUS current
        DESCRIPTION
        "Trap of PerEvt: ODU1_TCM5_ES"
        ::= { optixTrapsPER  14477 }

--  1.3.6.1.4.1.2011.2.25.3.40.40.30.14478
    perEvtOdu1Tcm5Ses NOTIFICATION-TYPE
        OBJECTS { rptEvtPeriod, rptEvtValue, rptEvtVldty, rptEvtDateTime, rptEvtObjType, rptEvtParaLen, rptEvtPara}
        STATUS current
        DESCRIPTION
        "Trap of PerEvt: ODU1_TCM5_SES"
        ::= { optixTrapsPER  14478 }

--  1.3.6.1.4.1.2011.2.25.3.40.40.30.14479
    perEvtOdu1Tcm5Uas NOTIFICATION-TYPE
        OBJECTS { rptEvtPeriod, rptEvtValue, rptEvtVldty, rptEvtDateTime, rptEvtObjType, rptEvtParaLen, rptEvtPara}
        STATUS current
        DESCRIPTION
        "Trap of PerEvt: ODU1_TCM5_UAS"
        ::= { optixTrapsPER  14479 }

--  1.3.6.1.4.1.2011.2.25.3.40.40.30.14480
    perEvtOdu1Tcm5Sesr NOTIFICATION-TYPE
        OBJECTS { rptEvtPeriod, rptEvtValue, rptEvtVldty, rptEvtDateTime, rptEvtObjType, rptEvtParaLen, rptEvtPara}
        STATUS current
        DESCRIPTION
        "Trap of PerEvt: ODU1_TCM5_SESR"
        ::= { optixTrapsPER  14480 }

--  1.3.6.1.4.1.2011.2.25.3.40.40.30.14481
    perEvtOdu1Tcm5Bber NOTIFICATION-TYPE
        OBJECTS { rptEvtPeriod, rptEvtValue, rptEvtVldty, rptEvtDateTime, rptEvtObjType, rptEvtParaLen, rptEvtPara}
        STATUS current
        DESCRIPTION
        "Trap of PerEvt: ODU1_TCM5_BBER"
        ::= { optixTrapsPER  14481 }

--  1.3.6.1.4.1.2011.2.25.3.40.40.30.14482
    perEvtOdu1Tcm6Bbe NOTIFICATION-TYPE
        OBJECTS { rptEvtPeriod, rptEvtValue, rptEvtVldty, rptEvtDateTime, rptEvtObjType, rptEvtParaLen, rptEvtPara}
        STATUS current
        DESCRIPTION
        "Trap of PerEvt: ODU1_TCM6_BBE"
        ::= { optixTrapsPER  14482 }

--  1.3.6.1.4.1.2011.2.25.3.40.40.30.14483
    perEvtOdu1Tcm6Es NOTIFICATION-TYPE
        OBJECTS { rptEvtPeriod, rptEvtValue, rptEvtVldty, rptEvtDateTime, rptEvtObjType, rptEvtParaLen, rptEvtPara}
        STATUS current
        DESCRIPTION
        "Trap of PerEvt: ODU1_TCM6_ES"
        ::= { optixTrapsPER  14483 }

--  1.3.6.1.4.1.2011.2.25.3.40.40.30.14484
    perEvtOdu1Tcm6Ses NOTIFICATION-TYPE
        OBJECTS { rptEvtPeriod, rptEvtValue, rptEvtVldty, rptEvtDateTime, rptEvtObjType, rptEvtParaLen, rptEvtPara}
        STATUS current
        DESCRIPTION
        "Trap of PerEvt: ODU1_TCM6_SES"
        ::= { optixTrapsPER  14484 }

--  1.3.6.1.4.1.2011.2.25.3.40.40.30.14485
    perEvtOdu1Tcm6Uas NOTIFICATION-TYPE
        OBJECTS { rptEvtPeriod, rptEvtValue, rptEvtVldty, rptEvtDateTime, rptEvtObjType, rptEvtParaLen, rptEvtPara}
        STATUS current
        DESCRIPTION
        "Trap of PerEvt: ODU1_TCM6_UAS"
        ::= { optixTrapsPER  14485 }

--  1.3.6.1.4.1.2011.2.25.3.40.40.30.14486
    perEvtOdu1Tcm6Sesr NOTIFICATION-TYPE
        OBJECTS { rptEvtPeriod, rptEvtValue, rptEvtVldty, rptEvtDateTime, rptEvtObjType, rptEvtParaLen, rptEvtPara}
        STATUS current
        DESCRIPTION
        "Trap of PerEvt: ODU1_TCM6_SESR"
        ::= { optixTrapsPER  14486 }

--  1.3.6.1.4.1.2011.2.25.3.40.40.30.14487
    perEvtOdu1Tcm6Bber NOTIFICATION-TYPE
        OBJECTS { rptEvtPeriod, rptEvtValue, rptEvtVldty, rptEvtDateTime, rptEvtObjType, rptEvtParaLen, rptEvtPara}
        STATUS current
        DESCRIPTION
        "Trap of PerEvt: ODU1_TCM6_BBER"
        ::= { optixTrapsPER  14487 }

--  1.3.6.1.4.1.2011.2.25.3.40.40.30.14488
    perEvtOdu1Tcm1Febbe NOTIFICATION-TYPE
        OBJECTS { rptEvtPeriod, rptEvtValue, rptEvtVldty, rptEvtDateTime, rptEvtObjType, rptEvtParaLen, rptEvtPara}
        STATUS current
        DESCRIPTION
        "Trap of PerEvt: ODU1_TCM1_FEBBE"
        ::= { optixTrapsPER  14488 }

--  1.3.6.1.4.1.2011.2.25.3.40.40.30.14489
    perEvtOdu1Tcm1Fees NOTIFICATION-TYPE
        OBJECTS { rptEvtPeriod, rptEvtValue, rptEvtVldty, rptEvtDateTime, rptEvtObjType, rptEvtParaLen, rptEvtPara}
        STATUS current
        DESCRIPTION
        "Trap of PerEvt: ODU1_TCM1_FEES"
        ::= { optixTrapsPER  14489 }

--  1.3.6.1.4.1.2011.2.25.3.40.40.30.14490
    perEvtOdu1Tcm1Feses NOTIFICATION-TYPE
        OBJECTS { rptEvtPeriod, rptEvtValue, rptEvtVldty, rptEvtDateTime, rptEvtObjType, rptEvtParaLen, rptEvtPara}
        STATUS current
        DESCRIPTION
        "Trap of PerEvt: ODU1_TCM1_FESES"
        ::= { optixTrapsPER  14490 }

--  1.3.6.1.4.1.2011.2.25.3.40.40.30.14491
    perEvtOdu1Tcm1Feuas NOTIFICATION-TYPE
        OBJECTS { rptEvtPeriod, rptEvtValue, rptEvtVldty, rptEvtDateTime, rptEvtObjType, rptEvtParaLen, rptEvtPara}
        STATUS current
        DESCRIPTION
        "Trap of PerEvt: ODU1_TCM1_FEUAS"
        ::= { optixTrapsPER  14491 }

--  1.3.6.1.4.1.2011.2.25.3.40.40.30.14492
    perEvtOdu1Tcm1Fesesr NOTIFICATION-TYPE
        OBJECTS { rptEvtPeriod, rptEvtValue, rptEvtVldty, rptEvtDateTime, rptEvtObjType, rptEvtParaLen, rptEvtPara}
        STATUS current
        DESCRIPTION
        "Trap of PerEvt: ODU1_TCM1_FESESR"
        ::= { optixTrapsPER  14492 }

--  1.3.6.1.4.1.2011.2.25.3.40.40.30.14493
    perEvtOdu1Tcm1Febber NOTIFICATION-TYPE
        OBJECTS { rptEvtPeriod, rptEvtValue, rptEvtVldty, rptEvtDateTime, rptEvtObjType, rptEvtParaLen, rptEvtPara}
        STATUS current
        DESCRIPTION
        "Trap of PerEvt: ODU1_TCM1_FEBBER"
        ::= { optixTrapsPER  14493 }

--  1.3.6.1.4.1.2011.2.25.3.40.40.30.14494
    perEvtOdu1Tcm2Febbe NOTIFICATION-TYPE
        OBJECTS { rptEvtPeriod, rptEvtValue, rptEvtVldty, rptEvtDateTime, rptEvtObjType, rptEvtParaLen, rptEvtPara}
        STATUS current
        DESCRIPTION
        "Trap of PerEvt: ODU1_TCM2_FEBBE"
        ::= { optixTrapsPER  14494 }

--  1.3.6.1.4.1.2011.2.25.3.40.40.30.14495
    perEvtOdu1Tcm2Fees NOTIFICATION-TYPE
        OBJECTS { rptEvtPeriod, rptEvtValue, rptEvtVldty, rptEvtDateTime, rptEvtObjType, rptEvtParaLen, rptEvtPara}
        STATUS current
        DESCRIPTION
        "Trap of PerEvt: ODU1_TCM2_FEES"
        ::= { optixTrapsPER  14495 }

--  1.3.6.1.4.1.2011.2.25.3.40.40.30.14496
    perEvtOdu1Tcm2Feses NOTIFICATION-TYPE
        OBJECTS { rptEvtPeriod, rptEvtValue, rptEvtVldty, rptEvtDateTime, rptEvtObjType, rptEvtParaLen, rptEvtPara}
        STATUS current
        DESCRIPTION
        "Trap of PerEvt: ODU1_TCM2_FESES"
        ::= { optixTrapsPER  14496 }

--  1.3.6.1.4.1.2011.2.25.3.40.40.30.14497
    perEvtOdu1Tcm2Feuas NOTIFICATION-TYPE
        OBJECTS { rptEvtPeriod, rptEvtValue, rptEvtVldty, rptEvtDateTime, rptEvtObjType, rptEvtParaLen, rptEvtPara}
        STATUS current
        DESCRIPTION
        "Trap of PerEvt: ODU1_TCM2_FEUAS"
        ::= { optixTrapsPER  14497 }

--  1.3.6.1.4.1.2011.2.25.3.40.40.30.14498
    perEvtOdu1Tcm2Fesesr NOTIFICATION-TYPE
        OBJECTS { rptEvtPeriod, rptEvtValue, rptEvtVldty, rptEvtDateTime, rptEvtObjType, rptEvtParaLen, rptEvtPara}
        STATUS current
        DESCRIPTION
        "Trap of PerEvt: ODU1_TCM2_FESESR"
        ::= { optixTrapsPER  14498 }

--  1.3.6.1.4.1.2011.2.25.3.40.40.30.14499
    perEvtOdu1Tcm2Febber NOTIFICATION-TYPE
        OBJECTS { rptEvtPeriod, rptEvtValue, rptEvtVldty, rptEvtDateTime, rptEvtObjType, rptEvtParaLen, rptEvtPara}
        STATUS current
        DESCRIPTION
        "Trap of PerEvt: ODU1_TCM2_FEBBER"
        ::= { optixTrapsPER  14499 }

--  1.3.6.1.4.1.2011.2.25.3.40.40.30.14500
    perEvtOdu1Tcm3Febbe NOTIFICATION-TYPE
        OBJECTS { rptEvtPeriod, rptEvtValue, rptEvtVldty, rptEvtDateTime, rptEvtObjType, rptEvtParaLen, rptEvtPara}
        STATUS current
        DESCRIPTION
        "Trap of PerEvt: ODU1_TCM3_FEBBE"
        ::= { optixTrapsPER  14500 }

--  1.3.6.1.4.1.2011.2.25.3.40.40.30.14501
    perEvtOdu1Tcm3Fees NOTIFICATION-TYPE
        OBJECTS { rptEvtPeriod, rptEvtValue, rptEvtVldty, rptEvtDateTime, rptEvtObjType, rptEvtParaLen, rptEvtPara}
        STATUS current
        DESCRIPTION
        "Trap of PerEvt: ODU1_TCM3_FEES"
        ::= { optixTrapsPER  14501 }

--  1.3.6.1.4.1.2011.2.25.3.40.40.30.14502
    perEvtOdu1Tcm3Feses NOTIFICATION-TYPE
        OBJECTS { rptEvtPeriod, rptEvtValue, rptEvtVldty, rptEvtDateTime, rptEvtObjType, rptEvtParaLen, rptEvtPara}
        STATUS current
        DESCRIPTION
        "Trap of PerEvt: ODU1_TCM3_FESES"
        ::= { optixTrapsPER  14502 }

--  1.3.6.1.4.1.2011.2.25.3.40.40.30.14503
    perEvtOdu1Tcm3Feuas NOTIFICATION-TYPE
        OBJECTS { rptEvtPeriod, rptEvtValue, rptEvtVldty, rptEvtDateTime, rptEvtObjType, rptEvtParaLen, rptEvtPara}
        STATUS current
        DESCRIPTION
        "Trap of PerEvt: ODU1_TCM3_FEUAS"
        ::= { optixTrapsPER  14503 }

--  1.3.6.1.4.1.2011.2.25.3.40.40.30.14504
    perEvtOdu1Tcm3Fesesr NOTIFICATION-TYPE
        OBJECTS { rptEvtPeriod, rptEvtValue, rptEvtVldty, rptEvtDateTime, rptEvtObjType, rptEvtParaLen, rptEvtPara}
        STATUS current
        DESCRIPTION
        "Trap of PerEvt: ODU1_TCM3_FESESR"
        ::= { optixTrapsPER  14504 }

--  1.3.6.1.4.1.2011.2.25.3.40.40.30.14505
    perEvtOdu1Tcm3Febber NOTIFICATION-TYPE
        OBJECTS { rptEvtPeriod, rptEvtValue, rptEvtVldty, rptEvtDateTime, rptEvtObjType, rptEvtParaLen, rptEvtPara}
        STATUS current
        DESCRIPTION
        "Trap of PerEvt: ODU1_TCM3_FEBBER"
        ::= { optixTrapsPER  14505 }

--  1.3.6.1.4.1.2011.2.25.3.40.40.30.14506
    perEvtOdu1Tcm4Febbe NOTIFICATION-TYPE
        OBJECTS { rptEvtPeriod, rptEvtValue, rptEvtVldty, rptEvtDateTime, rptEvtObjType, rptEvtParaLen, rptEvtPara}
        STATUS current
        DESCRIPTION
        "Trap of PerEvt: ODU1_TCM4_FEBBE"
        ::= { optixTrapsPER  14506 }

--  1.3.6.1.4.1.2011.2.25.3.40.40.30.14507
    perEvtOdu1Tcm4Fees NOTIFICATION-TYPE
        OBJECTS { rptEvtPeriod, rptEvtValue, rptEvtVldty, rptEvtDateTime, rptEvtObjType, rptEvtParaLen, rptEvtPara}
        STATUS current
        DESCRIPTION
        "Trap of PerEvt: ODU1_TCM4_FEES"
        ::= { optixTrapsPER  14507 }

--  1.3.6.1.4.1.2011.2.25.3.40.40.30.14508
    perEvtOdu1Tcm4Feses NOTIFICATION-TYPE
        OBJECTS { rptEvtPeriod, rptEvtValue, rptEvtVldty, rptEvtDateTime, rptEvtObjType, rptEvtParaLen, rptEvtPara}
        STATUS current
        DESCRIPTION
        "Trap of PerEvt: ODU1_TCM4_FESES"
        ::= { optixTrapsPER  14508 }

--  1.3.6.1.4.1.2011.2.25.3.40.40.30.14509
    perEvtOdu1Tcm4Feuas NOTIFICATION-TYPE
        OBJECTS { rptEvtPeriod, rptEvtValue, rptEvtVldty, rptEvtDateTime, rptEvtObjType, rptEvtParaLen, rptEvtPara}
        STATUS current
        DESCRIPTION
        "Trap of PerEvt: ODU1_TCM4_FEUAS"
        ::= { optixTrapsPER  14509 }

--  1.3.6.1.4.1.2011.2.25.3.40.40.30.14510
    perEvtOdu1Tcm4Fesesr NOTIFICATION-TYPE
        OBJECTS { rptEvtPeriod, rptEvtValue, rptEvtVldty, rptEvtDateTime, rptEvtObjType, rptEvtParaLen, rptEvtPara}
        STATUS current
        DESCRIPTION
        "Trap of PerEvt: ODU1_TCM4_FESESR"
        ::= { optixTrapsPER  14510 }

--  1.3.6.1.4.1.2011.2.25.3.40.40.30.14511
    perEvtOdu1Tcm4Febber NOTIFICATION-TYPE
        OBJECTS { rptEvtPeriod, rptEvtValue, rptEvtVldty, rptEvtDateTime, rptEvtObjType, rptEvtParaLen, rptEvtPara}
        STATUS current
        DESCRIPTION
        "Trap of PerEvt: ODU1_TCM4_FEBBER"
        ::= { optixTrapsPER  14511 }

--  1.3.6.1.4.1.2011.2.25.3.40.40.30.14512
    perEvtOdu1Tcm5Febbe NOTIFICATION-TYPE
        OBJECTS { rptEvtPeriod, rptEvtValue, rptEvtVldty, rptEvtDateTime, rptEvtObjType, rptEvtParaLen, rptEvtPara}
        STATUS current
        DESCRIPTION
        "Trap of PerEvt: ODU1_TCM5_FEBBE"
        ::= { optixTrapsPER  14512 }

--  1.3.6.1.4.1.2011.2.25.3.40.40.30.14513
    perEvtOdu1Tcm5Fees NOTIFICATION-TYPE
        OBJECTS { rptEvtPeriod, rptEvtValue, rptEvtVldty, rptEvtDateTime, rptEvtObjType, rptEvtParaLen, rptEvtPara}
        STATUS current
        DESCRIPTION
        "Trap of PerEvt: ODU1_TCM5_FEES"
        ::= { optixTrapsPER  14513 }

--  1.3.6.1.4.1.2011.2.25.3.40.40.30.14514
    perEvtOdu1Tcm5Feses NOTIFICATION-TYPE
        OBJECTS { rptEvtPeriod, rptEvtValue, rptEvtVldty, rptEvtDateTime, rptEvtObjType, rptEvtParaLen, rptEvtPara}
        STATUS current
        DESCRIPTION
        "Trap of PerEvt: ODU1_TCM5_FESES"
        ::= { optixTrapsPER  14514 }

--  1.3.6.1.4.1.2011.2.25.3.40.40.30.14515
    perEvtOdu1Tcm5Feuas NOTIFICATION-TYPE
        OBJECTS { rptEvtPeriod, rptEvtValue, rptEvtVldty, rptEvtDateTime, rptEvtObjType, rptEvtParaLen, rptEvtPara}
        STATUS current
        DESCRIPTION
        "Trap of PerEvt: ODU1_TCM5_FEUAS"
        ::= { optixTrapsPER  14515 }

--  1.3.6.1.4.1.2011.2.25.3.40.40.30.14516
    perEvtOdu1Tcm5Fesesr NOTIFICATION-TYPE
        OBJECTS { rptEvtPeriod, rptEvtValue, rptEvtVldty, rptEvtDateTime, rptEvtObjType, rptEvtParaLen, rptEvtPara}
        STATUS current
        DESCRIPTION
        "Trap of PerEvt: ODU1_TCM5_FESESR"
        ::= { optixTrapsPER  14516 }

--  1.3.6.1.4.1.2011.2.25.3.40.40.30.14517
    perEvtOdu1Tcm5Febber NOTIFICATION-TYPE
        OBJECTS { rptEvtPeriod, rptEvtValue, rptEvtVldty, rptEvtDateTime, rptEvtObjType, rptEvtParaLen, rptEvtPara}
        STATUS current
        DESCRIPTION
        "Trap of PerEvt: ODU1_TCM5_FEBBER"
        ::= { optixTrapsPER  14517 }

--  1.3.6.1.4.1.2011.2.25.3.40.40.30.14518
    perEvtOdu1Tcm6Febbe NOTIFICATION-TYPE
        OBJECTS { rptEvtPeriod, rptEvtValue, rptEvtVldty, rptEvtDateTime, rptEvtObjType, rptEvtParaLen, rptEvtPara}
        STATUS current
        DESCRIPTION
        "Trap of PerEvt: ODU1_TCM6_FEBBE"
        ::= { optixTrapsPER  14518 }

--  1.3.6.1.4.1.2011.2.25.3.40.40.30.14519
    perEvtOdu1Tcm6Fees NOTIFICATION-TYPE
        OBJECTS { rptEvtPeriod, rptEvtValue, rptEvtVldty, rptEvtDateTime, rptEvtObjType, rptEvtParaLen, rptEvtPara}
        STATUS current
        DESCRIPTION
        "Trap of PerEvt: ODU1_TCM6_FEES"
        ::= { optixTrapsPER  14519 }

--  1.3.6.1.4.1.2011.2.25.3.40.40.30.14520
    perEvtOdu1Tcm6Feses NOTIFICATION-TYPE
        OBJECTS { rptEvtPeriod, rptEvtValue, rptEvtVldty, rptEvtDateTime, rptEvtObjType, rptEvtParaLen, rptEvtPara}
        STATUS current
        DESCRIPTION
        "Trap of PerEvt: ODU1_TCM6_FESES"
        ::= { optixTrapsPER  14520 }

--  1.3.6.1.4.1.2011.2.25.3.40.40.30.14521
    perEvtOdu1Tcm6Feuas NOTIFICATION-TYPE
        OBJECTS { rptEvtPeriod, rptEvtValue, rptEvtVldty, rptEvtDateTime, rptEvtObjType, rptEvtParaLen, rptEvtPara}
        STATUS current
        DESCRIPTION
        "Trap of PerEvt: ODU1_TCM6_FEUAS"
        ::= { optixTrapsPER  14521 }

--  1.3.6.1.4.1.2011.2.25.3.40.40.30.14522
    perEvtOdu1Tcm6Fesesr NOTIFICATION-TYPE
        OBJECTS { rptEvtPeriod, rptEvtValue, rptEvtVldty, rptEvtDateTime, rptEvtObjType, rptEvtParaLen, rptEvtPara}
        STATUS current
        DESCRIPTION
        "Trap of PerEvt: ODU1_TCM6_FESESR"
        ::= { optixTrapsPER  14522 }

--  1.3.6.1.4.1.2011.2.25.3.40.40.30.14523
    perEvtOdu1Tcm6Febber NOTIFICATION-TYPE
        OBJECTS { rptEvtPeriod, rptEvtValue, rptEvtVldty, rptEvtDateTime, rptEvtObjType, rptEvtParaLen, rptEvtPara}
        STATUS current
        DESCRIPTION
        "Trap of PerEvt: ODU1_TCM6_FEBBER"
        ::= { optixTrapsPER  14523 }

--  1.3.6.1.4.1.2011.2.25.3.40.40.30.14608
    perEvtOdu2Tcm1Iaes NOTIFICATION-TYPE
        OBJECTS { rptEvtPeriod, rptEvtValue, rptEvtVldty, rptEvtDateTime, rptEvtObjType, rptEvtParaLen, rptEvtPara}
        STATUS current
        DESCRIPTION
        "Trap of PerEvt: ODU2_TCM1_IAES"
        ::= { optixTrapsPER  14608 }

--  1.3.6.1.4.1.2011.2.25.3.40.40.30.14609
    perEvtOdu2Tcm2Iaes NOTIFICATION-TYPE
        OBJECTS { rptEvtPeriod, rptEvtValue, rptEvtVldty, rptEvtDateTime, rptEvtObjType, rptEvtParaLen, rptEvtPara}
        STATUS current
        DESCRIPTION
        "Trap of PerEvt: ODU2_TCM2_IAES"
        ::= { optixTrapsPER  14609 }

--  1.3.6.1.4.1.2011.2.25.3.40.40.30.14610
    perEvtOdu2Tcm3Iaes NOTIFICATION-TYPE
        OBJECTS { rptEvtPeriod, rptEvtValue, rptEvtVldty, rptEvtDateTime, rptEvtObjType, rptEvtParaLen, rptEvtPara}
        STATUS current
        DESCRIPTION
        "Trap of PerEvt: ODU2_TCM3_IAES"
        ::= { optixTrapsPER  14610 }

--  1.3.6.1.4.1.2011.2.25.3.40.40.30.14611
    perEvtOdu2Tcm4Iaes NOTIFICATION-TYPE
        OBJECTS { rptEvtPeriod, rptEvtValue, rptEvtVldty, rptEvtDateTime, rptEvtObjType, rptEvtParaLen, rptEvtPara}
        STATUS current
        DESCRIPTION
        "Trap of PerEvt: ODU2_TCM4_IAES"
        ::= { optixTrapsPER  14611 }

--  1.3.6.1.4.1.2011.2.25.3.40.40.30.14612
    perEvtOdu2Tcm5Iaes NOTIFICATION-TYPE
        OBJECTS { rptEvtPeriod, rptEvtValue, rptEvtVldty, rptEvtDateTime, rptEvtObjType, rptEvtParaLen, rptEvtPara}
        STATUS current
        DESCRIPTION
        "Trap of PerEvt: ODU2_TCM5_IAES"
        ::= { optixTrapsPER  14612 }

--  1.3.6.1.4.1.2011.2.25.3.40.40.30.14613
    perEvtOdu2Tcm6Iaes NOTIFICATION-TYPE
        OBJECTS { rptEvtPeriod, rptEvtValue, rptEvtVldty, rptEvtDateTime, rptEvtObjType, rptEvtParaLen, rptEvtPara}
        STATUS current
        DESCRIPTION
        "Trap of PerEvt: ODU2_TCM6_IAES"
        ::= { optixTrapsPER  14613 }

--  1.3.6.1.4.1.2011.2.25.3.40.40.30.14614
    perEvtOdu2Tcm1Biaes NOTIFICATION-TYPE
        OBJECTS { rptEvtPeriod, rptEvtValue, rptEvtVldty, rptEvtDateTime, rptEvtObjType, rptEvtParaLen, rptEvtPara}
        STATUS current
        DESCRIPTION
        "Trap of PerEvt: ODU2_TCM1_BIAES"
        ::= { optixTrapsPER  14614 }

--  1.3.6.1.4.1.2011.2.25.3.40.40.30.14615
    perEvtOdu2Tcm2Biaes NOTIFICATION-TYPE
        OBJECTS { rptEvtPeriod, rptEvtValue, rptEvtVldty, rptEvtDateTime, rptEvtObjType, rptEvtParaLen, rptEvtPara}
        STATUS current
        DESCRIPTION
        "Trap of PerEvt: ODU2_TCM2_BIAES"
        ::= { optixTrapsPER  14615 }

--  1.3.6.1.4.1.2011.2.25.3.40.40.30.14616
    perEvtOdu2Tcm3Biaes NOTIFICATION-TYPE
        OBJECTS { rptEvtPeriod, rptEvtValue, rptEvtVldty, rptEvtDateTime, rptEvtObjType, rptEvtParaLen, rptEvtPara}
        STATUS current
        DESCRIPTION
        "Trap of PerEvt: ODU2_TCM3_BIAES"
        ::= { optixTrapsPER  14616 }

--  1.3.6.1.4.1.2011.2.25.3.40.40.30.14617
    perEvtOdu2Tcm4Biaes NOTIFICATION-TYPE
        OBJECTS { rptEvtPeriod, rptEvtValue, rptEvtVldty, rptEvtDateTime, rptEvtObjType, rptEvtParaLen, rptEvtPara}
        STATUS current
        DESCRIPTION
        "Trap of PerEvt: ODU2_TCM4_BIAES"
        ::= { optixTrapsPER  14617 }

--  1.3.6.1.4.1.2011.2.25.3.40.40.30.14618
    perEvtOdu2Tcm5Biaes NOTIFICATION-TYPE
        OBJECTS { rptEvtPeriod, rptEvtValue, rptEvtVldty, rptEvtDateTime, rptEvtObjType, rptEvtParaLen, rptEvtPara}
        STATUS current
        DESCRIPTION
        "Trap of PerEvt: ODU2_TCM5_BIAES"
        ::= { optixTrapsPER  14618 }

--  1.3.6.1.4.1.2011.2.25.3.40.40.30.14619
    perEvtOdu2Tcm6Biaes NOTIFICATION-TYPE
        OBJECTS { rptEvtPeriod, rptEvtValue, rptEvtVldty, rptEvtDateTime, rptEvtObjType, rptEvtParaLen, rptEvtPara}
        STATUS current
        DESCRIPTION
        "Trap of PerEvt: ODU2_TCM6_BIAES"
        ::= { optixTrapsPER  14619 }

--  1.3.6.1.4.1.2011.2.25.3.40.40.30.14620
    perEvtOdu2Tcm1Bbe NOTIFICATION-TYPE
        OBJECTS { rptEvtPeriod, rptEvtValue, rptEvtVldty, rptEvtDateTime, rptEvtObjType, rptEvtParaLen, rptEvtPara}
        STATUS current
        DESCRIPTION
        "Trap of PerEvt: ODU2_TCM1_BBE"
        ::= { optixTrapsPER  14620 }

--  1.3.6.1.4.1.2011.2.25.3.40.40.30.14621
    perEvtOdu2Tcm1Es NOTIFICATION-TYPE
        OBJECTS { rptEvtPeriod, rptEvtValue, rptEvtVldty, rptEvtDateTime, rptEvtObjType, rptEvtParaLen, rptEvtPara}
        STATUS current
        DESCRIPTION
        "Trap of PerEvt: ODU2_TCM1_ES"
        ::= { optixTrapsPER  14621 }

--  1.3.6.1.4.1.2011.2.25.3.40.40.30.14622
    perEvtOdu2Tcm1Ses NOTIFICATION-TYPE
        OBJECTS { rptEvtPeriod, rptEvtValue, rptEvtVldty, rptEvtDateTime, rptEvtObjType, rptEvtParaLen, rptEvtPara}
        STATUS current
        DESCRIPTION
        "Trap of PerEvt: ODU2_TCM1_SES"
        ::= { optixTrapsPER  14622 }

--  1.3.6.1.4.1.2011.2.25.3.40.40.30.14623
    perEvtOdu2Tcm1Uas NOTIFICATION-TYPE
        OBJECTS { rptEvtPeriod, rptEvtValue, rptEvtVldty, rptEvtDateTime, rptEvtObjType, rptEvtParaLen, rptEvtPara}
        STATUS current
        DESCRIPTION
        "Trap of PerEvt: ODU2_TCM1_UAS"
        ::= { optixTrapsPER  14623 }

--  1.3.6.1.4.1.2011.2.25.3.40.40.30.14624
    perEvtOdu2Tcm1Sesr NOTIFICATION-TYPE
        OBJECTS { rptEvtPeriod, rptEvtValue, rptEvtVldty, rptEvtDateTime, rptEvtObjType, rptEvtParaLen, rptEvtPara}
        STATUS current
        DESCRIPTION
        "Trap of PerEvt: ODU2_TCM1_SESR"
        ::= { optixTrapsPER  14624 }

--  1.3.6.1.4.1.2011.2.25.3.40.40.30.14625
    perEvtOdu2Tcm1Bber NOTIFICATION-TYPE
        OBJECTS { rptEvtPeriod, rptEvtValue, rptEvtVldty, rptEvtDateTime, rptEvtObjType, rptEvtParaLen, rptEvtPara}
        STATUS current
        DESCRIPTION
        "Trap of PerEvt: ODU2_TCM1_BBER"
        ::= { optixTrapsPER  14625 }

--  1.3.6.1.4.1.2011.2.25.3.40.40.30.14626
    perEvtOdu2Tcm2Bbe NOTIFICATION-TYPE
        OBJECTS { rptEvtPeriod, rptEvtValue, rptEvtVldty, rptEvtDateTime, rptEvtObjType, rptEvtParaLen, rptEvtPara}
        STATUS current
        DESCRIPTION
        "Trap of PerEvt: ODU2_TCM2_BBE"
        ::= { optixTrapsPER  14626 }

--  1.3.6.1.4.1.2011.2.25.3.40.40.30.14627
    perEvtOdu2Tcm2Es NOTIFICATION-TYPE
        OBJECTS { rptEvtPeriod, rptEvtValue, rptEvtVldty, rptEvtDateTime, rptEvtObjType, rptEvtParaLen, rptEvtPara}
        STATUS current
        DESCRIPTION
        "Trap of PerEvt: ODU2_TCM2_ES"
        ::= { optixTrapsPER  14627 }

--  1.3.6.1.4.1.2011.2.25.3.40.40.30.14628
    perEvtOdu2Tcm2Ses NOTIFICATION-TYPE
        OBJECTS { rptEvtPeriod, rptEvtValue, rptEvtVldty, rptEvtDateTime, rptEvtObjType, rptEvtParaLen, rptEvtPara}
        STATUS current
        DESCRIPTION
        "Trap of PerEvt: ODU2_TCM2_SES"
        ::= { optixTrapsPER  14628 }

--  1.3.6.1.4.1.2011.2.25.3.40.40.30.14629
    perEvtOdu2Tcm2Uas NOTIFICATION-TYPE
        OBJECTS { rptEvtPeriod, rptEvtValue, rptEvtVldty, rptEvtDateTime, rptEvtObjType, rptEvtParaLen, rptEvtPara}
        STATUS current
        DESCRIPTION
        "Trap of PerEvt: ODU2_TCM2_UAS"
        ::= { optixTrapsPER  14629 }

--  1.3.6.1.4.1.2011.2.25.3.40.40.30.14630
    perEvtOdu2Tcm2Sesr NOTIFICATION-TYPE
        OBJECTS { rptEvtPeriod, rptEvtValue, rptEvtVldty, rptEvtDateTime, rptEvtObjType, rptEvtParaLen, rptEvtPara}
        STATUS current
        DESCRIPTION
        "Trap of PerEvt: ODU2_TCM2_SESR"
        ::= { optixTrapsPER  14630 }

--  1.3.6.1.4.1.2011.2.25.3.40.40.30.14631
    perEvtOdu2Tcm2Bber NOTIFICATION-TYPE
        OBJECTS { rptEvtPeriod, rptEvtValue, rptEvtVldty, rptEvtDateTime, rptEvtObjType, rptEvtParaLen, rptEvtPara}
        STATUS current
        DESCRIPTION
        "Trap of PerEvt: ODU2_TCM2_BBER"
        ::= { optixTrapsPER  14631 }

--  1.3.6.1.4.1.2011.2.25.3.40.40.30.14632
    perEvtOdu2Tcm3Bbe NOTIFICATION-TYPE
        OBJECTS { rptEvtPeriod, rptEvtValue, rptEvtVldty, rptEvtDateTime, rptEvtObjType, rptEvtParaLen, rptEvtPara}
        STATUS current
        DESCRIPTION
        "Trap of PerEvt: ODU2_TCM3_BBE"
        ::= { optixTrapsPER  14632 }

--  1.3.6.1.4.1.2011.2.25.3.40.40.30.14633
    perEvtOdu2Tcm3Es NOTIFICATION-TYPE
        OBJECTS { rptEvtPeriod, rptEvtValue, rptEvtVldty, rptEvtDateTime, rptEvtObjType, rptEvtParaLen, rptEvtPara}
        STATUS current
        DESCRIPTION
        "Trap of PerEvt: ODU2_TCM3_ES"
        ::= { optixTrapsPER  14633 }

--  1.3.6.1.4.1.2011.2.25.3.40.40.30.14634
    perEvtOdu2Tcm3Ses NOTIFICATION-TYPE
        OBJECTS { rptEvtPeriod, rptEvtValue, rptEvtVldty, rptEvtDateTime, rptEvtObjType, rptEvtParaLen, rptEvtPara}
        STATUS current
        DESCRIPTION
        "Trap of PerEvt: ODU2_TCM3_SES"
        ::= { optixTrapsPER  14634 }

--  1.3.6.1.4.1.2011.2.25.3.40.40.30.14635
    perEvtOdu2Tcm3Uas NOTIFICATION-TYPE
        OBJECTS { rptEvtPeriod, rptEvtValue, rptEvtVldty, rptEvtDateTime, rptEvtObjType, rptEvtParaLen, rptEvtPara}
        STATUS current
        DESCRIPTION
        "Trap of PerEvt: ODU2_TCM3_UAS"
        ::= { optixTrapsPER  14635 }

--  1.3.6.1.4.1.2011.2.25.3.40.40.30.14636
    perEvtOdu2Tcm3Sesr NOTIFICATION-TYPE
        OBJECTS { rptEvtPeriod, rptEvtValue, rptEvtVldty, rptEvtDateTime, rptEvtObjType, rptEvtParaLen, rptEvtPara}
        STATUS current
        DESCRIPTION
        "Trap of PerEvt: ODU2_TCM3_SESR"
        ::= { optixTrapsPER  14636 }

--  1.3.6.1.4.1.2011.2.25.3.40.40.30.14637
    perEvtOdu2Tcm3Bber NOTIFICATION-TYPE
        OBJECTS { rptEvtPeriod, rptEvtValue, rptEvtVldty, rptEvtDateTime, rptEvtObjType, rptEvtParaLen, rptEvtPara}
        STATUS current
        DESCRIPTION
        "Trap of PerEvt: ODU2_TCM3_BBER"
        ::= { optixTrapsPER  14637 }

--  1.3.6.1.4.1.2011.2.25.3.40.40.30.14638
    perEvtOdu2Tcm4Bbe NOTIFICATION-TYPE
        OBJECTS { rptEvtPeriod, rptEvtValue, rptEvtVldty, rptEvtDateTime, rptEvtObjType, rptEvtParaLen, rptEvtPara}
        STATUS current
        DESCRIPTION
        "Trap of PerEvt: ODU2_TCM4_BBE"
        ::= { optixTrapsPER  14638 }

--  1.3.6.1.4.1.2011.2.25.3.40.40.30.14639
    perEvtOdu2Tcm4Es NOTIFICATION-TYPE
        OBJECTS { rptEvtPeriod, rptEvtValue, rptEvtVldty, rptEvtDateTime, rptEvtObjType, rptEvtParaLen, rptEvtPara}
        STATUS current
        DESCRIPTION
        "Trap of PerEvt: ODU2_TCM4_ES"
        ::= { optixTrapsPER  14639 }

--  1.3.6.1.4.1.2011.2.25.3.40.40.30.14640
    perEvtOdu2Tcm4Ses NOTIFICATION-TYPE
        OBJECTS { rptEvtPeriod, rptEvtValue, rptEvtVldty, rptEvtDateTime, rptEvtObjType, rptEvtParaLen, rptEvtPara}
        STATUS current
        DESCRIPTION
        "Trap of PerEvt: ODU2_TCM4_SES"
        ::= { optixTrapsPER  14640 }

--  1.3.6.1.4.1.2011.2.25.3.40.40.30.14641
    perEvtOdu2Tcm4Uas NOTIFICATION-TYPE
        OBJECTS { rptEvtPeriod, rptEvtValue, rptEvtVldty, rptEvtDateTime, rptEvtObjType, rptEvtParaLen, rptEvtPara}
        STATUS current
        DESCRIPTION
        "Trap of PerEvt: ODU2_TCM4_UAS"
        ::= { optixTrapsPER  14641 }

--  1.3.6.1.4.1.2011.2.25.3.40.40.30.14642
    perEvtOdu2Tcm4Sesr NOTIFICATION-TYPE
        OBJECTS { rptEvtPeriod, rptEvtValue, rptEvtVldty, rptEvtDateTime, rptEvtObjType, rptEvtParaLen, rptEvtPara}
        STATUS current
        DESCRIPTION
        "Trap of PerEvt: ODU2_TCM4_SESR"
        ::= { optixTrapsPER  14642 }

--  1.3.6.1.4.1.2011.2.25.3.40.40.30.14643
    perEvtOdu2Tcm4Bber NOTIFICATION-TYPE
        OBJECTS { rptEvtPeriod, rptEvtValue, rptEvtVldty, rptEvtDateTime, rptEvtObjType, rptEvtParaLen, rptEvtPara}
        STATUS current
        DESCRIPTION
        "Trap of PerEvt: ODU2_TCM4_BBER"
        ::= { optixTrapsPER  14643 }

--  1.3.6.1.4.1.2011.2.25.3.40.40.30.14644
    perEvtOdu2Tcm5Bbe NOTIFICATION-TYPE
        OBJECTS { rptEvtPeriod, rptEvtValue, rptEvtVldty, rptEvtDateTime, rptEvtObjType, rptEvtParaLen, rptEvtPara}
        STATUS current
        DESCRIPTION
        "Trap of PerEvt: ODU2_TCM5_BBE"
        ::= { optixTrapsPER  14644 }

--  1.3.6.1.4.1.2011.2.25.3.40.40.30.14645
    perEvtOdu2Tcm5Es NOTIFICATION-TYPE
        OBJECTS { rptEvtPeriod, rptEvtValue, rptEvtVldty, rptEvtDateTime, rptEvtObjType, rptEvtParaLen, rptEvtPara}
        STATUS current
        DESCRIPTION
        "Trap of PerEvt: ODU2_TCM5_ES"
        ::= { optixTrapsPER  14645 }

--  1.3.6.1.4.1.2011.2.25.3.40.40.30.14646
    perEvtOdu2Tcm5Ses NOTIFICATION-TYPE
        OBJECTS { rptEvtPeriod, rptEvtValue, rptEvtVldty, rptEvtDateTime, rptEvtObjType, rptEvtParaLen, rptEvtPara}
        STATUS current
        DESCRIPTION
        "Trap of PerEvt: ODU2_TCM5_SES"
        ::= { optixTrapsPER  14646 }

--  1.3.6.1.4.1.2011.2.25.3.40.40.30.14647
    perEvtOdu2Tcm5Uas NOTIFICATION-TYPE
        OBJECTS { rptEvtPeriod, rptEvtValue, rptEvtVldty, rptEvtDateTime, rptEvtObjType, rptEvtParaLen, rptEvtPara}
        STATUS current
        DESCRIPTION
        "Trap of PerEvt: ODU2_TCM5_UAS"
        ::= { optixTrapsPER  14647 }

--  1.3.6.1.4.1.2011.2.25.3.40.40.30.14648
    perEvtOdu2Tcm5Sesr NOTIFICATION-TYPE
        OBJECTS { rptEvtPeriod, rptEvtValue, rptEvtVldty, rptEvtDateTime, rptEvtObjType, rptEvtParaLen, rptEvtPara}
        STATUS current
        DESCRIPTION
        "Trap of PerEvt: ODU2_TCM5_SESR"
        ::= { optixTrapsPER  14648 }

--  1.3.6.1.4.1.2011.2.25.3.40.40.30.14649
    perEvtOdu2Tcm5Bber NOTIFICATION-TYPE
        OBJECTS { rptEvtPeriod, rptEvtValue, rptEvtVldty, rptEvtDateTime, rptEvtObjType, rptEvtParaLen, rptEvtPara}
        STATUS current
        DESCRIPTION
        "Trap of PerEvt: ODU2_TCM5_BBER"
        ::= { optixTrapsPER  14649 }

--  1.3.6.1.4.1.2011.2.25.3.40.40.30.14650
    perEvtOdu2Tcm6Bbe NOTIFICATION-TYPE
        OBJECTS { rptEvtPeriod, rptEvtValue, rptEvtVldty, rptEvtDateTime, rptEvtObjType, rptEvtParaLen, rptEvtPara}
        STATUS current
        DESCRIPTION
        "Trap of PerEvt: ODU2_TCM6_BBE"
        ::= { optixTrapsPER  14650 }

--  1.3.6.1.4.1.2011.2.25.3.40.40.30.14651
    perEvtOdu2Tcm6Es NOTIFICATION-TYPE
        OBJECTS { rptEvtPeriod, rptEvtValue, rptEvtVldty, rptEvtDateTime, rptEvtObjType, rptEvtParaLen, rptEvtPara}
        STATUS current
        DESCRIPTION
        "Trap of PerEvt: ODU2_TCM6_ES"
        ::= { optixTrapsPER  14651 }

--  1.3.6.1.4.1.2011.2.25.3.40.40.30.14652
    perEvtOdu2Tcm6Ses NOTIFICATION-TYPE
        OBJECTS { rptEvtPeriod, rptEvtValue, rptEvtVldty, rptEvtDateTime, rptEvtObjType, rptEvtParaLen, rptEvtPara}
        STATUS current
        DESCRIPTION
        "Trap of PerEvt: ODU2_TCM6_SES"
        ::= { optixTrapsPER  14652 }

--  1.3.6.1.4.1.2011.2.25.3.40.40.30.14653
    perEvtOdu2Tcm6Uas NOTIFICATION-TYPE
        OBJECTS { rptEvtPeriod, rptEvtValue, rptEvtVldty, rptEvtDateTime, rptEvtObjType, rptEvtParaLen, rptEvtPara}
        STATUS current
        DESCRIPTION
        "Trap of PerEvt: ODU2_TCM6_UAS"
        ::= { optixTrapsPER  14653 }

--  1.3.6.1.4.1.2011.2.25.3.40.40.30.14654
    perEvtOdu2Tcm6Sesr NOTIFICATION-TYPE
        OBJECTS { rptEvtPeriod, rptEvtValue, rptEvtVldty, rptEvtDateTime, rptEvtObjType, rptEvtParaLen, rptEvtPara}
        STATUS current
        DESCRIPTION
        "Trap of PerEvt: ODU2_TCM6_SESR"
        ::= { optixTrapsPER  14654 }

--  1.3.6.1.4.1.2011.2.25.3.40.40.30.14655
    perEvtOdu2Tcm6Bber NOTIFICATION-TYPE
        OBJECTS { rptEvtPeriod, rptEvtValue, rptEvtVldty, rptEvtDateTime, rptEvtObjType, rptEvtParaLen, rptEvtPara}
        STATUS current
        DESCRIPTION
        "Trap of PerEvt: ODU2_TCM6_BBER"
        ::= { optixTrapsPER  14655 }

--  1.3.6.1.4.1.2011.2.25.3.40.40.30.14656
    perEvtOdu2Tcm1Febbe NOTIFICATION-TYPE
        OBJECTS { rptEvtPeriod, rptEvtValue, rptEvtVldty, rptEvtDateTime, rptEvtObjType, rptEvtParaLen, rptEvtPara}
        STATUS current
        DESCRIPTION
        "Trap of PerEvt: ODU2_TCM1_FEBBE"
        ::= { optixTrapsPER  14656 }

--  1.3.6.1.4.1.2011.2.25.3.40.40.30.14657
    perEvtOdu2Tcm1Fees NOTIFICATION-TYPE
        OBJECTS { rptEvtPeriod, rptEvtValue, rptEvtVldty, rptEvtDateTime, rptEvtObjType, rptEvtParaLen, rptEvtPara}
        STATUS current
        DESCRIPTION
        "Trap of PerEvt: ODU2_TCM1_FEES"
        ::= { optixTrapsPER  14657 }

--  1.3.6.1.4.1.2011.2.25.3.40.40.30.14658
    perEvtOdu2Tcm1Feses NOTIFICATION-TYPE
        OBJECTS { rptEvtPeriod, rptEvtValue, rptEvtVldty, rptEvtDateTime, rptEvtObjType, rptEvtParaLen, rptEvtPara}
        STATUS current
        DESCRIPTION
        "Trap of PerEvt: ODU2_TCM1_FESES"
        ::= { optixTrapsPER  14658 }

--  1.3.6.1.4.1.2011.2.25.3.40.40.30.14659
    perEvtOdu2Tcm1Feuas NOTIFICATION-TYPE
        OBJECTS { rptEvtPeriod, rptEvtValue, rptEvtVldty, rptEvtDateTime, rptEvtObjType, rptEvtParaLen, rptEvtPara}
        STATUS current
        DESCRIPTION
        "Trap of PerEvt: ODU2_TCM1_FEUAS"
        ::= { optixTrapsPER  14659 }

--  1.3.6.1.4.1.2011.2.25.3.40.40.30.14660
    perEvtOdu2Tcm1Fesesr NOTIFICATION-TYPE
        OBJECTS { rptEvtPeriod, rptEvtValue, rptEvtVldty, rptEvtDateTime, rptEvtObjType, rptEvtParaLen, rptEvtPara}
        STATUS current
        DESCRIPTION
        "Trap of PerEvt: ODU2_TCM1_FESESR"
        ::= { optixTrapsPER  14660 }

--  1.3.6.1.4.1.2011.2.25.3.40.40.30.14661
    perEvtOdu2Tcm1Febber NOTIFICATION-TYPE
        OBJECTS { rptEvtPeriod, rptEvtValue, rptEvtVldty, rptEvtDateTime, rptEvtObjType, rptEvtParaLen, rptEvtPara}
        STATUS current
        DESCRIPTION
        "Trap of PerEvt: ODU2_TCM1_FEBBER"
        ::= { optixTrapsPER  14661 }

--  1.3.6.1.4.1.2011.2.25.3.40.40.30.14662
    perEvtOdu2Tcm2Febbe NOTIFICATION-TYPE
        OBJECTS { rptEvtPeriod, rptEvtValue, rptEvtVldty, rptEvtDateTime, rptEvtObjType, rptEvtParaLen, rptEvtPara}
        STATUS current
        DESCRIPTION
        "Trap of PerEvt: ODU2_TCM2_FEBBE"
        ::= { optixTrapsPER  14662 }

--  1.3.6.1.4.1.2011.2.25.3.40.40.30.14663
    perEvtOdu2Tcm2Fees NOTIFICATION-TYPE
        OBJECTS { rptEvtPeriod, rptEvtValue, rptEvtVldty, rptEvtDateTime, rptEvtObjType, rptEvtParaLen, rptEvtPara}
        STATUS current
        DESCRIPTION
        "Trap of PerEvt: ODU2_TCM2_FEES"
        ::= { optixTrapsPER  14663 }

--  1.3.6.1.4.1.2011.2.25.3.40.40.30.14664
    perEvtOdu2Tcm2Feses NOTIFICATION-TYPE
        OBJECTS { rptEvtPeriod, rptEvtValue, rptEvtVldty, rptEvtDateTime, rptEvtObjType, rptEvtParaLen, rptEvtPara}
        STATUS current
        DESCRIPTION
        "Trap of PerEvt: ODU2_TCM2_FESES"
        ::= { optixTrapsPER  14664 }

--  1.3.6.1.4.1.2011.2.25.3.40.40.30.14665
    perEvtOdu2Tcm2Feuas NOTIFICATION-TYPE
        OBJECTS { rptEvtPeriod, rptEvtValue, rptEvtVldty, rptEvtDateTime, rptEvtObjType, rptEvtParaLen, rptEvtPara}
        STATUS current
        DESCRIPTION
        "Trap of PerEvt: ODU2_TCM2_FEUAS"
        ::= { optixTrapsPER  14665 }

--  1.3.6.1.4.1.2011.2.25.3.40.40.30.14666
    perEvtOdu2Tcm2Fesesr NOTIFICATION-TYPE
        OBJECTS { rptEvtPeriod, rptEvtValue, rptEvtVldty, rptEvtDateTime, rptEvtObjType, rptEvtParaLen, rptEvtPara}
        STATUS current
        DESCRIPTION
        "Trap of PerEvt: ODU2_TCM2_FESESR"
        ::= { optixTrapsPER  14666 }

--  1.3.6.1.4.1.2011.2.25.3.40.40.30.14667
    perEvtOdu2Tcm2Febber NOTIFICATION-TYPE
        OBJECTS { rptEvtPeriod, rptEvtValue, rptEvtVldty, rptEvtDateTime, rptEvtObjType, rptEvtParaLen, rptEvtPara}
        STATUS current
        DESCRIPTION
        "Trap of PerEvt: ODU2_TCM2_FEBBER"
        ::= { optixTrapsPER  14667 }

--  1.3.6.1.4.1.2011.2.25.3.40.40.30.14668
    perEvtOdu2Tcm3Febbe NOTIFICATION-TYPE
        OBJECTS { rptEvtPeriod, rptEvtValue, rptEvtVldty, rptEvtDateTime, rptEvtObjType, rptEvtParaLen, rptEvtPara}
        STATUS current
        DESCRIPTION
        "Trap of PerEvt: ODU2_TCM3_FEBBE"
        ::= { optixTrapsPER  14668 }

--  1.3.6.1.4.1.2011.2.25.3.40.40.30.14669
    perEvtOdu2Tcm3Fees NOTIFICATION-TYPE
        OBJECTS { rptEvtPeriod, rptEvtValue, rptEvtVldty, rptEvtDateTime, rptEvtObjType, rptEvtParaLen, rptEvtPara}
        STATUS current
        DESCRIPTION
        "Trap of PerEvt: ODU2_TCM3_FEES"
        ::= { optixTrapsPER  14669 }

--  1.3.6.1.4.1.2011.2.25.3.40.40.30.14670
    perEvtOdu2Tcm3Feses NOTIFICATION-TYPE
        OBJECTS { rptEvtPeriod, rptEvtValue, rptEvtVldty, rptEvtDateTime, rptEvtObjType, rptEvtParaLen, rptEvtPara}
        STATUS current
        DESCRIPTION
        "Trap of PerEvt: ODU2_TCM3_FESES"
        ::= { optixTrapsPER  14670 }

--  1.3.6.1.4.1.2011.2.25.3.40.40.30.14671
    perEvtOdu2Tcm3Feuas NOTIFICATION-TYPE
        OBJECTS { rptEvtPeriod, rptEvtValue, rptEvtVldty, rptEvtDateTime, rptEvtObjType, rptEvtParaLen, rptEvtPara}
        STATUS current
        DESCRIPTION
        "Trap of PerEvt: ODU2_TCM3_FEUAS"
        ::= { optixTrapsPER  14671 }

--  1.3.6.1.4.1.2011.2.25.3.40.40.30.14672
    perEvtOdu2Tcm3Fesesr NOTIFICATION-TYPE
        OBJECTS { rptEvtPeriod, rptEvtValue, rptEvtVldty, rptEvtDateTime, rptEvtObjType, rptEvtParaLen, rptEvtPara}
        STATUS current
        DESCRIPTION
        "Trap of PerEvt: ODU2_TCM3_FESESR"
        ::= { optixTrapsPER  14672 }

--  1.3.6.1.4.1.2011.2.25.3.40.40.30.14673
    perEvtOdu2Tcm3Febber NOTIFICATION-TYPE
        OBJECTS { rptEvtPeriod, rptEvtValue, rptEvtVldty, rptEvtDateTime, rptEvtObjType, rptEvtParaLen, rptEvtPara}
        STATUS current
        DESCRIPTION
        "Trap of PerEvt: ODU2_TCM3_FEBBER"
        ::= { optixTrapsPER  14673 }

--  1.3.6.1.4.1.2011.2.25.3.40.40.30.14674
    perEvtOdu2Tcm4Febbe NOTIFICATION-TYPE
        OBJECTS { rptEvtPeriod, rptEvtValue, rptEvtVldty, rptEvtDateTime, rptEvtObjType, rptEvtParaLen, rptEvtPara}
        STATUS current
        DESCRIPTION
        "Trap of PerEvt: ODU2_TCM4_FEBBE"
        ::= { optixTrapsPER  14674 }

--  1.3.6.1.4.1.2011.2.25.3.40.40.30.14675
    perEvtOdu2Tcm4Fees NOTIFICATION-TYPE
        OBJECTS { rptEvtPeriod, rptEvtValue, rptEvtVldty, rptEvtDateTime, rptEvtObjType, rptEvtParaLen, rptEvtPara}
        STATUS current
        DESCRIPTION
        "Trap of PerEvt: ODU2_TCM4_FEES"
        ::= { optixTrapsPER  14675 }

--  1.3.6.1.4.1.2011.2.25.3.40.40.30.14676
    perEvtOdu2Tcm4Feses NOTIFICATION-TYPE
        OBJECTS { rptEvtPeriod, rptEvtValue, rptEvtVldty, rptEvtDateTime, rptEvtObjType, rptEvtParaLen, rptEvtPara}
        STATUS current
        DESCRIPTION
        "Trap of PerEvt: ODU2_TCM4_FESES"
        ::= { optixTrapsPER  14676 }

--  1.3.6.1.4.1.2011.2.25.3.40.40.30.14677
    perEvtOdu2Tcm4Feuas NOTIFICATION-TYPE
        OBJECTS { rptEvtPeriod, rptEvtValue, rptEvtVldty, rptEvtDateTime, rptEvtObjType, rptEvtParaLen, rptEvtPara}
        STATUS current
        DESCRIPTION
        "Trap of PerEvt: ODU2_TCM4_FEUAS"
        ::= { optixTrapsPER  14677 }

--  1.3.6.1.4.1.2011.2.25.3.40.40.30.14678
    perEvtOdu2Tcm4Fesesr NOTIFICATION-TYPE
        OBJECTS { rptEvtPeriod, rptEvtValue, rptEvtVldty, rptEvtDateTime, rptEvtObjType, rptEvtParaLen, rptEvtPara}
        STATUS current
        DESCRIPTION
        "Trap of PerEvt: ODU2_TCM4_FESESR"
        ::= { optixTrapsPER  14678 }

--  1.3.6.1.4.1.2011.2.25.3.40.40.30.14679
    perEvtOdu2Tcm4Febber NOTIFICATION-TYPE
        OBJECTS { rptEvtPeriod, rptEvtValue, rptEvtVldty, rptEvtDateTime, rptEvtObjType, rptEvtParaLen, rptEvtPara}
        STATUS current
        DESCRIPTION
        "Trap of PerEvt: ODU2_TCM4_FEBBER"
        ::= { optixTrapsPER  14679 }

--  1.3.6.1.4.1.2011.2.25.3.40.40.30.14680
    perEvtOdu2Tcm5Febbe NOTIFICATION-TYPE
        OBJECTS { rptEvtPeriod, rptEvtValue, rptEvtVldty, rptEvtDateTime, rptEvtObjType, rptEvtParaLen, rptEvtPara}
        STATUS current
        DESCRIPTION
        "Trap of PerEvt: ODU2_TCM5_FEBBE"
        ::= { optixTrapsPER  14680 }

--  1.3.6.1.4.1.2011.2.25.3.40.40.30.14681
    perEvtOdu2Tcm5Fees NOTIFICATION-TYPE
        OBJECTS { rptEvtPeriod, rptEvtValue, rptEvtVldty, rptEvtDateTime, rptEvtObjType, rptEvtParaLen, rptEvtPara}
        STATUS current
        DESCRIPTION
        "Trap of PerEvt: ODU2_TCM5_FEES"
        ::= { optixTrapsPER  14681 }

--  1.3.6.1.4.1.2011.2.25.3.40.40.30.14682
    perEvtOdu2Tcm5Feses NOTIFICATION-TYPE
        OBJECTS { rptEvtPeriod, rptEvtValue, rptEvtVldty, rptEvtDateTime, rptEvtObjType, rptEvtParaLen, rptEvtPara}
        STATUS current
        DESCRIPTION
        "Trap of PerEvt: ODU2_TCM5_FESES"
        ::= { optixTrapsPER  14682 }

--  1.3.6.1.4.1.2011.2.25.3.40.40.30.14683
    perEvtOdu2Tcm5Feuas NOTIFICATION-TYPE
        OBJECTS { rptEvtPeriod, rptEvtValue, rptEvtVldty, rptEvtDateTime, rptEvtObjType, rptEvtParaLen, rptEvtPara}
        STATUS current
        DESCRIPTION
        "Trap of PerEvt: ODU2_TCM5_FEUAS"
        ::= { optixTrapsPER  14683 }

--  1.3.6.1.4.1.2011.2.25.3.40.40.30.14684
    perEvtOdu2Tcm5Fesesr NOTIFICATION-TYPE
        OBJECTS { rptEvtPeriod, rptEvtValue, rptEvtVldty, rptEvtDateTime, rptEvtObjType, rptEvtParaLen, rptEvtPara}
        STATUS current
        DESCRIPTION
        "Trap of PerEvt: ODU2_TCM5_FESESR"
        ::= { optixTrapsPER  14684 }

--  1.3.6.1.4.1.2011.2.25.3.40.40.30.14685
    perEvtOdu2Tcm5Febber NOTIFICATION-TYPE
        OBJECTS { rptEvtPeriod, rptEvtValue, rptEvtVldty, rptEvtDateTime, rptEvtObjType, rptEvtParaLen, rptEvtPara}
        STATUS current
        DESCRIPTION
        "Trap of PerEvt: ODU2_TCM5_FEBBER"
        ::= { optixTrapsPER  14685 }

--  1.3.6.1.4.1.2011.2.25.3.40.40.30.14686
    perEvtOdu2Tcm6Febbe NOTIFICATION-TYPE
        OBJECTS { rptEvtPeriod, rptEvtValue, rptEvtVldty, rptEvtDateTime, rptEvtObjType, rptEvtParaLen, rptEvtPara}
        STATUS current
        DESCRIPTION
        "Trap of PerEvt: ODU2_TCM6_FEBBE"
        ::= { optixTrapsPER  14686 }

--  1.3.6.1.4.1.2011.2.25.3.40.40.30.14687
    perEvtOdu2Tcm6Fees NOTIFICATION-TYPE
        OBJECTS { rptEvtPeriod, rptEvtValue, rptEvtVldty, rptEvtDateTime, rptEvtObjType, rptEvtParaLen, rptEvtPara}
        STATUS current
        DESCRIPTION
        "Trap of PerEvt: ODU2_TCM6_FEES"
        ::= { optixTrapsPER  14687 }

--  1.3.6.1.4.1.2011.2.25.3.40.40.30.14688
    perEvtOdu2Tcm6Feses NOTIFICATION-TYPE
        OBJECTS { rptEvtPeriod, rptEvtValue, rptEvtVldty, rptEvtDateTime, rptEvtObjType, rptEvtParaLen, rptEvtPara}
        STATUS current
        DESCRIPTION
        "Trap of PerEvt: ODU2_TCM6_FESES"
        ::= { optixTrapsPER  14688 }

--  1.3.6.1.4.1.2011.2.25.3.40.40.30.14689
    perEvtOdu2Tcm6Feuas NOTIFICATION-TYPE
        OBJECTS { rptEvtPeriod, rptEvtValue, rptEvtVldty, rptEvtDateTime, rptEvtObjType, rptEvtParaLen, rptEvtPara}
        STATUS current
        DESCRIPTION
        "Trap of PerEvt: ODU2_TCM6_FEUAS"
        ::= { optixTrapsPER  14689 }

--  1.3.6.1.4.1.2011.2.25.3.40.40.30.14690
    perEvtOdu2Tcm6Fesesr NOTIFICATION-TYPE
        OBJECTS { rptEvtPeriod, rptEvtValue, rptEvtVldty, rptEvtDateTime, rptEvtObjType, rptEvtParaLen, rptEvtPara}
        STATUS current
        DESCRIPTION
        "Trap of PerEvt: ODU2_TCM6_FESESR"
        ::= { optixTrapsPER  14690 }

--  1.3.6.1.4.1.2011.2.25.3.40.40.30.14691
    perEvtOdu2Tcm6Febber NOTIFICATION-TYPE
        OBJECTS { rptEvtPeriod, rptEvtValue, rptEvtVldty, rptEvtDateTime, rptEvtObjType, rptEvtParaLen, rptEvtPara}
        STATUS current
        DESCRIPTION
        "Trap of PerEvt: ODU2_TCM6_FEBBER"
        ::= { optixTrapsPER  14691 }

--  1.3.6.1.4.1.2011.2.25.3.40.40.30.14692
    perEvtOdu3Tcm1Iaes NOTIFICATION-TYPE
        OBJECTS { rptEvtPeriod, rptEvtValue, rptEvtVldty, rptEvtDateTime, rptEvtObjType, rptEvtParaLen, rptEvtPara}
        STATUS current
        DESCRIPTION
        "Trap of PerEvt: ODU3_TCM1_IAES"
        ::= { optixTrapsPER  14692 }

--  1.3.6.1.4.1.2011.2.25.3.40.40.30.14693
    perEvtOdu3Tcm2Iaes NOTIFICATION-TYPE
        OBJECTS { rptEvtPeriod, rptEvtValue, rptEvtVldty, rptEvtDateTime, rptEvtObjType, rptEvtParaLen, rptEvtPara}
        STATUS current
        DESCRIPTION
        "Trap of PerEvt: ODU3_TCM2_IAES"
        ::= { optixTrapsPER  14693 }

--  1.3.6.1.4.1.2011.2.25.3.40.40.30.14694
    perEvtOdu3Tcm3Iaes NOTIFICATION-TYPE
        OBJECTS { rptEvtPeriod, rptEvtValue, rptEvtVldty, rptEvtDateTime, rptEvtObjType, rptEvtParaLen, rptEvtPara}
        STATUS current
        DESCRIPTION
        "Trap of PerEvt: ODU3_TCM3_IAES"
        ::= { optixTrapsPER  14694 }

--  1.3.6.1.4.1.2011.2.25.3.40.40.30.14695
    perEvtOdu3Tcm4Iaes NOTIFICATION-TYPE
        OBJECTS { rptEvtPeriod, rptEvtValue, rptEvtVldty, rptEvtDateTime, rptEvtObjType, rptEvtParaLen, rptEvtPara}
        STATUS current
        DESCRIPTION
        "Trap of PerEvt: ODU3_TCM4_IAES"
        ::= { optixTrapsPER  14695 }

--  1.3.6.1.4.1.2011.2.25.3.40.40.30.14696
    perEvtOdu3Tcm5Iaes NOTIFICATION-TYPE
        OBJECTS { rptEvtPeriod, rptEvtValue, rptEvtVldty, rptEvtDateTime, rptEvtObjType, rptEvtParaLen, rptEvtPara}
        STATUS current
        DESCRIPTION
        "Trap of PerEvt: ODU3_TCM5_IAES"
        ::= { optixTrapsPER  14696 }

--  1.3.6.1.4.1.2011.2.25.3.40.40.30.14697
    perEvtOdu3Tcm6Iaes NOTIFICATION-TYPE
        OBJECTS { rptEvtPeriod, rptEvtValue, rptEvtVldty, rptEvtDateTime, rptEvtObjType, rptEvtParaLen, rptEvtPara}
        STATUS current
        DESCRIPTION
        "Trap of PerEvt: ODU3_TCM6_IAES"
        ::= { optixTrapsPER  14697 }

--  1.3.6.1.4.1.2011.2.25.3.40.40.30.14698
    perEvtOdu3Tcm1Biaes NOTIFICATION-TYPE
        OBJECTS { rptEvtPeriod, rptEvtValue, rptEvtVldty, rptEvtDateTime, rptEvtObjType, rptEvtParaLen, rptEvtPara}
        STATUS current
        DESCRIPTION
        "Trap of PerEvt: ODU3_TCM1_BIAES"
        ::= { optixTrapsPER  14698 }

--  1.3.6.1.4.1.2011.2.25.3.40.40.30.14699
    perEvtOdu3Tcm2Biaes NOTIFICATION-TYPE
        OBJECTS { rptEvtPeriod, rptEvtValue, rptEvtVldty, rptEvtDateTime, rptEvtObjType, rptEvtParaLen, rptEvtPara}
        STATUS current
        DESCRIPTION
        "Trap of PerEvt: ODU3_TCM2_BIAES"
        ::= { optixTrapsPER  14699 }

--  1.3.6.1.4.1.2011.2.25.3.40.40.30.14700
    perEvtOdu3Tcm3Biaes NOTIFICATION-TYPE
        OBJECTS { rptEvtPeriod, rptEvtValue, rptEvtVldty, rptEvtDateTime, rptEvtObjType, rptEvtParaLen, rptEvtPara}
        STATUS current
        DESCRIPTION
        "Trap of PerEvt: ODU3_TCM3_BIAES"
        ::= { optixTrapsPER  14700 }

--  1.3.6.1.4.1.2011.2.25.3.40.40.30.14701
    perEvtOdu3Tcm4Biaes NOTIFICATION-TYPE
        OBJECTS { rptEvtPeriod, rptEvtValue, rptEvtVldty, rptEvtDateTime, rptEvtObjType, rptEvtParaLen, rptEvtPara}
        STATUS current
        DESCRIPTION
        "Trap of PerEvt: ODU3_TCM4_BIAES"
        ::= { optixTrapsPER  14701 }

--  1.3.6.1.4.1.2011.2.25.3.40.40.30.14702
    perEvtOdu3Tcm5Biaes NOTIFICATION-TYPE
        OBJECTS { rptEvtPeriod, rptEvtValue, rptEvtVldty, rptEvtDateTime, rptEvtObjType, rptEvtParaLen, rptEvtPara}
        STATUS current
        DESCRIPTION
        "Trap of PerEvt: ODU3_TCM5_BIAES"
        ::= { optixTrapsPER  14702 }

--  1.3.6.1.4.1.2011.2.25.3.40.40.30.14703
    perEvtOdu3Tcm6Biaes NOTIFICATION-TYPE
        OBJECTS { rptEvtPeriod, rptEvtValue, rptEvtVldty, rptEvtDateTime, rptEvtObjType, rptEvtParaLen, rptEvtPara}
        STATUS current
        DESCRIPTION
        "Trap of PerEvt: ODU3_TCM6_BIAES"
        ::= { optixTrapsPER  14703 }

--  1.3.6.1.4.1.2011.2.25.3.40.40.30.14704
    perEvtOdu3Tcm1Bbe NOTIFICATION-TYPE
        OBJECTS { rptEvtPeriod, rptEvtValue, rptEvtVldty, rptEvtDateTime, rptEvtObjType, rptEvtParaLen, rptEvtPara}
        STATUS current
        DESCRIPTION
        "Trap of PerEvt: ODU3_TCM1_BBE"
        ::= { optixTrapsPER  14704 }

--  1.3.6.1.4.1.2011.2.25.3.40.40.30.14705
    perEvtOdu3Tcm1Es NOTIFICATION-TYPE
        OBJECTS { rptEvtPeriod, rptEvtValue, rptEvtVldty, rptEvtDateTime, rptEvtObjType, rptEvtParaLen, rptEvtPara}
        STATUS current
        DESCRIPTION
        "Trap of PerEvt: ODU3_TCM1_ES"
        ::= { optixTrapsPER  14705 }

--  1.3.6.1.4.1.2011.2.25.3.40.40.30.14706
    perEvtOdu3Tcm1Ses NOTIFICATION-TYPE
        OBJECTS { rptEvtPeriod, rptEvtValue, rptEvtVldty, rptEvtDateTime, rptEvtObjType, rptEvtParaLen, rptEvtPara}
        STATUS current
        DESCRIPTION
        "Trap of PerEvt: ODU3_TCM1_SES"
        ::= { optixTrapsPER  14706 }

--  1.3.6.1.4.1.2011.2.25.3.40.40.30.14707
    perEvtOdu3Tcm1Uas NOTIFICATION-TYPE
        OBJECTS { rptEvtPeriod, rptEvtValue, rptEvtVldty, rptEvtDateTime, rptEvtObjType, rptEvtParaLen, rptEvtPara}
        STATUS current
        DESCRIPTION
        "Trap of PerEvt: ODU3_TCM1_UAS"
        ::= { optixTrapsPER  14707 }

--  1.3.6.1.4.1.2011.2.25.3.40.40.30.14708
    perEvtOdu3Tcm1Sesr NOTIFICATION-TYPE
        OBJECTS { rptEvtPeriod, rptEvtValue, rptEvtVldty, rptEvtDateTime, rptEvtObjType, rptEvtParaLen, rptEvtPara}
        STATUS current
        DESCRIPTION
        "Trap of PerEvt: ODU3_TCM1_SESR"
        ::= { optixTrapsPER  14708 }

--  1.3.6.1.4.1.2011.2.25.3.40.40.30.14709
    perEvtOdu3Tcm1Bber NOTIFICATION-TYPE
        OBJECTS { rptEvtPeriod, rptEvtValue, rptEvtVldty, rptEvtDateTime, rptEvtObjType, rptEvtParaLen, rptEvtPara}
        STATUS current
        DESCRIPTION
        "Trap of PerEvt: ODU3_TCM1_BBER"
        ::= { optixTrapsPER  14709 }

--  1.3.6.1.4.1.2011.2.25.3.40.40.30.14710
    perEvtOdu3Tcm2Bbe NOTIFICATION-TYPE
        OBJECTS { rptEvtPeriod, rptEvtValue, rptEvtVldty, rptEvtDateTime, rptEvtObjType, rptEvtParaLen, rptEvtPara}
        STATUS current
        DESCRIPTION
        "Trap of PerEvt: ODU3_TCM2_BBE"
        ::= { optixTrapsPER  14710 }

--  1.3.6.1.4.1.2011.2.25.3.40.40.30.14711
    perEvtOdu3Tcm2Es NOTIFICATION-TYPE
        OBJECTS { rptEvtPeriod, rptEvtValue, rptEvtVldty, rptEvtDateTime, rptEvtObjType, rptEvtParaLen, rptEvtPara}
        STATUS current
        DESCRIPTION
        "Trap of PerEvt: ODU3_TCM2_ES"
        ::= { optixTrapsPER  14711 }

--  1.3.6.1.4.1.2011.2.25.3.40.40.30.14712
    perEvtOdu3Tcm2Ses NOTIFICATION-TYPE
        OBJECTS { rptEvtPeriod, rptEvtValue, rptEvtVldty, rptEvtDateTime, rptEvtObjType, rptEvtParaLen, rptEvtPara}
        STATUS current
        DESCRIPTION
        "Trap of PerEvt: ODU3_TCM2_SES"
        ::= { optixTrapsPER  14712 }

--  1.3.6.1.4.1.2011.2.25.3.40.40.30.14713
    perEvtOdu3Tcm2Uas NOTIFICATION-TYPE
        OBJECTS { rptEvtPeriod, rptEvtValue, rptEvtVldty, rptEvtDateTime, rptEvtObjType, rptEvtParaLen, rptEvtPara}
        STATUS current
        DESCRIPTION
        "Trap of PerEvt: ODU3_TCM2_UAS"
        ::= { optixTrapsPER  14713 }

--  1.3.6.1.4.1.2011.2.25.3.40.40.30.14714
    perEvtOdu3Tcm2Sesr NOTIFICATION-TYPE
        OBJECTS { rptEvtPeriod, rptEvtValue, rptEvtVldty, rptEvtDateTime, rptEvtObjType, rptEvtParaLen, rptEvtPara}
        STATUS current
        DESCRIPTION
        "Trap of PerEvt: ODU3_TCM2_SESR"
        ::= { optixTrapsPER  14714 }

--  1.3.6.1.4.1.2011.2.25.3.40.40.30.14715
    perEvtOdu3Tcm2Bber NOTIFICATION-TYPE
        OBJECTS { rptEvtPeriod, rptEvtValue, rptEvtVldty, rptEvtDateTime, rptEvtObjType, rptEvtParaLen, rptEvtPara}
        STATUS current
        DESCRIPTION
        "Trap of PerEvt: ODU3_TCM2_BBER"
        ::= { optixTrapsPER  14715 }

--  1.3.6.1.4.1.2011.2.25.3.40.40.30.14716
    perEvtOdu3Tcm3Bbe NOTIFICATION-TYPE
        OBJECTS { rptEvtPeriod, rptEvtValue, rptEvtVldty, rptEvtDateTime, rptEvtObjType, rptEvtParaLen, rptEvtPara}
        STATUS current
        DESCRIPTION
        "Trap of PerEvt: ODU3_TCM3_BBE"
        ::= { optixTrapsPER  14716 }

--  1.3.6.1.4.1.2011.2.25.3.40.40.30.14717
    perEvtOdu3Tcm3Es NOTIFICATION-TYPE
        OBJECTS { rptEvtPeriod, rptEvtValue, rptEvtVldty, rptEvtDateTime, rptEvtObjType, rptEvtParaLen, rptEvtPara}
        STATUS current
        DESCRIPTION
        "Trap of PerEvt: ODU3_TCM3_ES"
        ::= { optixTrapsPER  14717 }

--  1.3.6.1.4.1.2011.2.25.3.40.40.30.14718
    perEvtOdu3Tcm3Ses NOTIFICATION-TYPE
        OBJECTS { rptEvtPeriod, rptEvtValue, rptEvtVldty, rptEvtDateTime, rptEvtObjType, rptEvtParaLen, rptEvtPara}
        STATUS current
        DESCRIPTION
        "Trap of PerEvt: ODU3_TCM3_SES"
        ::= { optixTrapsPER  14718 }

--  1.3.6.1.4.1.2011.2.25.3.40.40.30.14719
    perEvtOdu3Tcm3Uas NOTIFICATION-TYPE
        OBJECTS { rptEvtPeriod, rptEvtValue, rptEvtVldty, rptEvtDateTime, rptEvtObjType, rptEvtParaLen, rptEvtPara}
        STATUS current
        DESCRIPTION
        "Trap of PerEvt: ODU3_TCM3_UAS"
        ::= { optixTrapsPER  14719 }

--  1.3.6.1.4.1.2011.2.25.3.40.40.30.14720
    perEvtOdu3Tcm3Sesr NOTIFICATION-TYPE
        OBJECTS { rptEvtPeriod, rptEvtValue, rptEvtVldty, rptEvtDateTime, rptEvtObjType, rptEvtParaLen, rptEvtPara}
        STATUS current
        DESCRIPTION
        "Trap of PerEvt: ODU3_TCM3_SESR"
        ::= { optixTrapsPER  14720 }

--  1.3.6.1.4.1.2011.2.25.3.40.40.30.14721
    perEvtOdu3Tcm3Bber NOTIFICATION-TYPE
        OBJECTS { rptEvtPeriod, rptEvtValue, rptEvtVldty, rptEvtDateTime, rptEvtObjType, rptEvtParaLen, rptEvtPara}
        STATUS current
        DESCRIPTION
        "Trap of PerEvt: ODU3_TCM3_BBER"
        ::= { optixTrapsPER  14721 }

--  1.3.6.1.4.1.2011.2.25.3.40.40.30.14722
    perEvtOdu3Tcm4Bbe NOTIFICATION-TYPE
        OBJECTS { rptEvtPeriod, rptEvtValue, rptEvtVldty, rptEvtDateTime, rptEvtObjType, rptEvtParaLen, rptEvtPara}
        STATUS current
        DESCRIPTION
        "Trap of PerEvt: ODU3_TCM4_BBE"
        ::= { optixTrapsPER  14722 }

--  1.3.6.1.4.1.2011.2.25.3.40.40.30.14723
    perEvtOdu3Tcm4Es NOTIFICATION-TYPE
        OBJECTS { rptEvtPeriod, rptEvtValue, rptEvtVldty, rptEvtDateTime, rptEvtObjType, rptEvtParaLen, rptEvtPara}
        STATUS current
        DESCRIPTION
        "Trap of PerEvt: ODU3_TCM4_ES"
        ::= { optixTrapsPER  14723 }

--  1.3.6.1.4.1.2011.2.25.3.40.40.30.14724
    perEvtOdu3Tcm4Ses NOTIFICATION-TYPE
        OBJECTS { rptEvtPeriod, rptEvtValue, rptEvtVldty, rptEvtDateTime, rptEvtObjType, rptEvtParaLen, rptEvtPara}
        STATUS current
        DESCRIPTION
        "Trap of PerEvt: ODU3_TCM4_SES"
        ::= { optixTrapsPER  14724 }

--  1.3.6.1.4.1.2011.2.25.3.40.40.30.14725
    perEvtOdu3Tcm4Uas NOTIFICATION-TYPE
        OBJECTS { rptEvtPeriod, rptEvtValue, rptEvtVldty, rptEvtDateTime, rptEvtObjType, rptEvtParaLen, rptEvtPara}
        STATUS current
        DESCRIPTION
        "Trap of PerEvt: ODU3_TCM4_UAS"
        ::= { optixTrapsPER  14725 }

--  1.3.6.1.4.1.2011.2.25.3.40.40.30.14726
    perEvtOdu3Tcm4Sesr NOTIFICATION-TYPE
        OBJECTS { rptEvtPeriod, rptEvtValue, rptEvtVldty, rptEvtDateTime, rptEvtObjType, rptEvtParaLen, rptEvtPara}
        STATUS current
        DESCRIPTION
        "Trap of PerEvt: ODU3_TCM4_SESR"
        ::= { optixTrapsPER  14726 }

--  1.3.6.1.4.1.2011.2.25.3.40.40.30.14727
    perEvtOdu3Tcm4Bber NOTIFICATION-TYPE
        OBJECTS { rptEvtPeriod, rptEvtValue, rptEvtVldty, rptEvtDateTime, rptEvtObjType, rptEvtParaLen, rptEvtPara}
        STATUS current
        DESCRIPTION
        "Trap of PerEvt: ODU3_TCM4_BBER"
        ::= { optixTrapsPER  14727 }

--  1.3.6.1.4.1.2011.2.25.3.40.40.30.14728
    perEvtOdu3Tcm5Bbe NOTIFICATION-TYPE
        OBJECTS { rptEvtPeriod, rptEvtValue, rptEvtVldty, rptEvtDateTime, rptEvtObjType, rptEvtParaLen, rptEvtPara}
        STATUS current
        DESCRIPTION
        "Trap of PerEvt: ODU3_TCM5_BBE"
        ::= { optixTrapsPER  14728 }

--  1.3.6.1.4.1.2011.2.25.3.40.40.30.14729
    perEvtOdu3Tcm5Es NOTIFICATION-TYPE
        OBJECTS { rptEvtPeriod, rptEvtValue, rptEvtVldty, rptEvtDateTime, rptEvtObjType, rptEvtParaLen, rptEvtPara}
        STATUS current
        DESCRIPTION
        "Trap of PerEvt: ODU3_TCM5_ES"
        ::= { optixTrapsPER  14729 }

--  1.3.6.1.4.1.2011.2.25.3.40.40.30.14730
    perEvtOdu3Tcm5Ses NOTIFICATION-TYPE
        OBJECTS { rptEvtPeriod, rptEvtValue, rptEvtVldty, rptEvtDateTime, rptEvtObjType, rptEvtParaLen, rptEvtPara}
        STATUS current
        DESCRIPTION
        "Trap of PerEvt: ODU3_TCM5_SES"
        ::= { optixTrapsPER  14730 }

--  1.3.6.1.4.1.2011.2.25.3.40.40.30.14731
    perEvtOdu3Tcm5Uas NOTIFICATION-TYPE
        OBJECTS { rptEvtPeriod, rptEvtValue, rptEvtVldty, rptEvtDateTime, rptEvtObjType, rptEvtParaLen, rptEvtPara}
        STATUS current
        DESCRIPTION
        "Trap of PerEvt: ODU3_TCM5_UAS"
        ::= { optixTrapsPER  14731 }

--  1.3.6.1.4.1.2011.2.25.3.40.40.30.14732
    perEvtOdu3Tcm5Sesr NOTIFICATION-TYPE
        OBJECTS { rptEvtPeriod, rptEvtValue, rptEvtVldty, rptEvtDateTime, rptEvtObjType, rptEvtParaLen, rptEvtPara}
        STATUS current
        DESCRIPTION
        "Trap of PerEvt: ODU3_TCM5_SESR"
        ::= { optixTrapsPER  14732 }

--  1.3.6.1.4.1.2011.2.25.3.40.40.30.14733
    perEvtOdu3Tcm5Bber NOTIFICATION-TYPE
        OBJECTS { rptEvtPeriod, rptEvtValue, rptEvtVldty, rptEvtDateTime, rptEvtObjType, rptEvtParaLen, rptEvtPara}
        STATUS current
        DESCRIPTION
        "Trap of PerEvt: ODU3_TCM5_BBER"
        ::= { optixTrapsPER  14733 }

--  1.3.6.1.4.1.2011.2.25.3.40.40.30.14734
    perEvtOdu3Tcm6Bbe NOTIFICATION-TYPE
        OBJECTS { rptEvtPeriod, rptEvtValue, rptEvtVldty, rptEvtDateTime, rptEvtObjType, rptEvtParaLen, rptEvtPara}
        STATUS current
        DESCRIPTION
        "Trap of PerEvt: ODU3_TCM6_BBE"
        ::= { optixTrapsPER  14734 }

--  1.3.6.1.4.1.2011.2.25.3.40.40.30.14735
    perEvtOdu3Tcm6Es NOTIFICATION-TYPE
        OBJECTS { rptEvtPeriod, rptEvtValue, rptEvtVldty, rptEvtDateTime, rptEvtObjType, rptEvtParaLen, rptEvtPara}
        STATUS current
        DESCRIPTION
        "Trap of PerEvt: ODU3_TCM6_ES"
        ::= { optixTrapsPER  14735 }

--  1.3.6.1.4.1.2011.2.25.3.40.40.30.14736
    perEvtOdu3Tcm6Ses NOTIFICATION-TYPE
        OBJECTS { rptEvtPeriod, rptEvtValue, rptEvtVldty, rptEvtDateTime, rptEvtObjType, rptEvtParaLen, rptEvtPara}
        STATUS current
        DESCRIPTION
        "Trap of PerEvt: ODU3_TCM6_SES"
        ::= { optixTrapsPER  14736 }

--  1.3.6.1.4.1.2011.2.25.3.40.40.30.14737
    perEvtOdu3Tcm6Uas NOTIFICATION-TYPE
        OBJECTS { rptEvtPeriod, rptEvtValue, rptEvtVldty, rptEvtDateTime, rptEvtObjType, rptEvtParaLen, rptEvtPara}
        STATUS current
        DESCRIPTION
        "Trap of PerEvt: ODU3_TCM6_UAS"
        ::= { optixTrapsPER  14737 }

--  1.3.6.1.4.1.2011.2.25.3.40.40.30.14738
    perEvtOdu3Tcm6Sesr NOTIFICATION-TYPE
        OBJECTS { rptEvtPeriod, rptEvtValue, rptEvtVldty, rptEvtDateTime, rptEvtObjType, rptEvtParaLen, rptEvtPara}
        STATUS current
        DESCRIPTION
        "Trap of PerEvt: ODU3_TCM6_SESR"
        ::= { optixTrapsPER  14738 }

--  1.3.6.1.4.1.2011.2.25.3.40.40.30.14739
    perEvtOdu3Tcm6Bber NOTIFICATION-TYPE
        OBJECTS { rptEvtPeriod, rptEvtValue, rptEvtVldty, rptEvtDateTime, rptEvtObjType, rptEvtParaLen, rptEvtPara}
        STATUS current
        DESCRIPTION
        "Trap of PerEvt: ODU3_TCM6_BBER"
        ::= { optixTrapsPER  14739 }

--  1.3.6.1.4.1.2011.2.25.3.40.40.30.14740
    perEvtOdu3Tcm1Febbe NOTIFICATION-TYPE
        OBJECTS { rptEvtPeriod, rptEvtValue, rptEvtVldty, rptEvtDateTime, rptEvtObjType, rptEvtParaLen, rptEvtPara}
        STATUS current
        DESCRIPTION
        "Trap of PerEvt: ODU3_TCM1_FEBBE"
        ::= { optixTrapsPER  14740 }

--  1.3.6.1.4.1.2011.2.25.3.40.40.30.14741
    perEvtOdu3Tcm1Fees NOTIFICATION-TYPE
        OBJECTS { rptEvtPeriod, rptEvtValue, rptEvtVldty, rptEvtDateTime, rptEvtObjType, rptEvtParaLen, rptEvtPara}
        STATUS current
        DESCRIPTION
        "Trap of PerEvt: ODU3_TCM1_FEES"
        ::= { optixTrapsPER  14741 }

--  1.3.6.1.4.1.2011.2.25.3.40.40.30.14742
    perEvtOdu3Tcm1Feses NOTIFICATION-TYPE
        OBJECTS { rptEvtPeriod, rptEvtValue, rptEvtVldty, rptEvtDateTime, rptEvtObjType, rptEvtParaLen, rptEvtPara}
        STATUS current
        DESCRIPTION
        "Trap of PerEvt: ODU3_TCM1_FESES"
        ::= { optixTrapsPER  14742 }

--  1.3.6.1.4.1.2011.2.25.3.40.40.30.14743
    perEvtOdu3Tcm1Feuas NOTIFICATION-TYPE
        OBJECTS { rptEvtPeriod, rptEvtValue, rptEvtVldty, rptEvtDateTime, rptEvtObjType, rptEvtParaLen, rptEvtPara}
        STATUS current
        DESCRIPTION
        "Trap of PerEvt: ODU3_TCM1_FEUAS"
        ::= { optixTrapsPER  14743 }

--  1.3.6.1.4.1.2011.2.25.3.40.40.30.14744
    perEvtOdu3Tcm1Fesesr NOTIFICATION-TYPE
        OBJECTS { rptEvtPeriod, rptEvtValue, rptEvtVldty, rptEvtDateTime, rptEvtObjType, rptEvtParaLen, rptEvtPara}
        STATUS current
        DESCRIPTION
        "Trap of PerEvt: ODU3_TCM1_FESESR"
        ::= { optixTrapsPER  14744 }

--  1.3.6.1.4.1.2011.2.25.3.40.40.30.14745
    perEvtOdu3Tcm1Febber NOTIFICATION-TYPE
        OBJECTS { rptEvtPeriod, rptEvtValue, rptEvtVldty, rptEvtDateTime, rptEvtObjType, rptEvtParaLen, rptEvtPara}
        STATUS current
        DESCRIPTION
        "Trap of PerEvt: ODU3_TCM1_FEBBER"
        ::= { optixTrapsPER  14745 }

--  1.3.6.1.4.1.2011.2.25.3.40.40.30.14746
    perEvtOdu3Tcm2Febbe NOTIFICATION-TYPE
        OBJECTS { rptEvtPeriod, rptEvtValue, rptEvtVldty, rptEvtDateTime, rptEvtObjType, rptEvtParaLen, rptEvtPara}
        STATUS current
        DESCRIPTION
        "Trap of PerEvt: ODU3_TCM2_FEBBE"
        ::= { optixTrapsPER  14746 }

--  1.3.6.1.4.1.2011.2.25.3.40.40.30.14747
    perEvtOdu3Tcm2Fees NOTIFICATION-TYPE
        OBJECTS { rptEvtPeriod, rptEvtValue, rptEvtVldty, rptEvtDateTime, rptEvtObjType, rptEvtParaLen, rptEvtPara}
        STATUS current
        DESCRIPTION
        "Trap of PerEvt: ODU3_TCM2_FEES"
        ::= { optixTrapsPER  14747 }

--  1.3.6.1.4.1.2011.2.25.3.40.40.30.14748
    perEvtOdu3Tcm2Feses NOTIFICATION-TYPE
        OBJECTS { rptEvtPeriod, rptEvtValue, rptEvtVldty, rptEvtDateTime, rptEvtObjType, rptEvtParaLen, rptEvtPara}
        STATUS current
        DESCRIPTION
        "Trap of PerEvt: ODU3_TCM2_FESES"
        ::= { optixTrapsPER  14748 }

--  1.3.6.1.4.1.2011.2.25.3.40.40.30.14749
    perEvtOdu3Tcm2Feuas NOTIFICATION-TYPE
        OBJECTS { rptEvtPeriod, rptEvtValue, rptEvtVldty, rptEvtDateTime, rptEvtObjType, rptEvtParaLen, rptEvtPara}
        STATUS current
        DESCRIPTION
        "Trap of PerEvt: ODU3_TCM2_FEUAS"
        ::= { optixTrapsPER  14749 }

--  1.3.6.1.4.1.2011.2.25.3.40.40.30.14750
    perEvtOdu3Tcm2Fesesr NOTIFICATION-TYPE
        OBJECTS { rptEvtPeriod, rptEvtValue, rptEvtVldty, rptEvtDateTime, rptEvtObjType, rptEvtParaLen, rptEvtPara}
        STATUS current
        DESCRIPTION
        "Trap of PerEvt: ODU3_TCM2_FESESR"
        ::= { optixTrapsPER  14750 }

--  1.3.6.1.4.1.2011.2.25.3.40.40.30.14751
    perEvtOdu3Tcm2Febber NOTIFICATION-TYPE
        OBJECTS { rptEvtPeriod, rptEvtValue, rptEvtVldty, rptEvtDateTime, rptEvtObjType, rptEvtParaLen, rptEvtPara}
        STATUS current
        DESCRIPTION
        "Trap of PerEvt: ODU3_TCM2_FEBBER"
        ::= { optixTrapsPER  14751 }

--  1.3.6.1.4.1.2011.2.25.3.40.40.30.14752
    perEvtOdu3Tcm3Febbe NOTIFICATION-TYPE
        OBJECTS { rptEvtPeriod, rptEvtValue, rptEvtVldty, rptEvtDateTime, rptEvtObjType, rptEvtParaLen, rptEvtPara}
        STATUS current
        DESCRIPTION
        "Trap of PerEvt: ODU3_TCM3_FEBBE"
        ::= { optixTrapsPER  14752 }

--  1.3.6.1.4.1.2011.2.25.3.40.40.30.14753
    perEvtOdu3Tcm3Fees NOTIFICATION-TYPE
        OBJECTS { rptEvtPeriod, rptEvtValue, rptEvtVldty, rptEvtDateTime, rptEvtObjType, rptEvtParaLen, rptEvtPara}
        STATUS current
        DESCRIPTION
        "Trap of PerEvt: ODU3_TCM3_FEES"
        ::= { optixTrapsPER  14753 }

--  1.3.6.1.4.1.2011.2.25.3.40.40.30.14754
    perEvtOdu3Tcm3Feses NOTIFICATION-TYPE
        OBJECTS { rptEvtPeriod, rptEvtValue, rptEvtVldty, rptEvtDateTime, rptEvtObjType, rptEvtParaLen, rptEvtPara}
        STATUS current
        DESCRIPTION
        "Trap of PerEvt: ODU3_TCM3_FESES"
        ::= { optixTrapsPER  14754 }

--  1.3.6.1.4.1.2011.2.25.3.40.40.30.14755
    perEvtOdu3Tcm3Feuas NOTIFICATION-TYPE
        OBJECTS { rptEvtPeriod, rptEvtValue, rptEvtVldty, rptEvtDateTime, rptEvtObjType, rptEvtParaLen, rptEvtPara}
        STATUS current
        DESCRIPTION
        "Trap of PerEvt: ODU3_TCM3_FEUAS"
        ::= { optixTrapsPER  14755 }

--  1.3.6.1.4.1.2011.2.25.3.40.40.30.14756
    perEvtOdu3Tcm3Fesesr NOTIFICATION-TYPE
        OBJECTS { rptEvtPeriod, rptEvtValue, rptEvtVldty, rptEvtDateTime, rptEvtObjType, rptEvtParaLen, rptEvtPara}
        STATUS current
        DESCRIPTION
        "Trap of PerEvt: ODU3_TCM3_FESESR"
        ::= { optixTrapsPER  14756 }

--  1.3.6.1.4.1.2011.2.25.3.40.40.30.14757
    perEvtOdu3Tcm3Febber NOTIFICATION-TYPE
        OBJECTS { rptEvtPeriod, rptEvtValue, rptEvtVldty, rptEvtDateTime, rptEvtObjType, rptEvtParaLen, rptEvtPara}
        STATUS current
        DESCRIPTION
        "Trap of PerEvt: ODU3_TCM3_FEBBER"
        ::= { optixTrapsPER  14757 }

--  1.3.6.1.4.1.2011.2.25.3.40.40.30.14758
    perEvtOdu3Tcm4Febbe NOTIFICATION-TYPE
        OBJECTS { rptEvtPeriod, rptEvtValue, rptEvtVldty, rptEvtDateTime, rptEvtObjType, rptEvtParaLen, rptEvtPara}
        STATUS current
        DESCRIPTION
        "Trap of PerEvt: ODU3_TCM4_FEBBE"
        ::= { optixTrapsPER  14758 }

--  1.3.6.1.4.1.2011.2.25.3.40.40.30.14759
    perEvtOdu3Tcm4Fees NOTIFICATION-TYPE
        OBJECTS { rptEvtPeriod, rptEvtValue, rptEvtVldty, rptEvtDateTime, rptEvtObjType, rptEvtParaLen, rptEvtPara}
        STATUS current
        DESCRIPTION
        "Trap of PerEvt: ODU3_TCM4_FEES"
        ::= { optixTrapsPER  14759 }

--  1.3.6.1.4.1.2011.2.25.3.40.40.30.14760
    perEvtOdu3Tcm4Feses NOTIFICATION-TYPE
        OBJECTS { rptEvtPeriod, rptEvtValue, rptEvtVldty, rptEvtDateTime, rptEvtObjType, rptEvtParaLen, rptEvtPara}
        STATUS current
        DESCRIPTION
        "Trap of PerEvt: ODU3_TCM4_FESES"
        ::= { optixTrapsPER  14760 }

--  1.3.6.1.4.1.2011.2.25.3.40.40.30.14761
    perEvtOdu3Tcm4Feuas NOTIFICATION-TYPE
        OBJECTS { rptEvtPeriod, rptEvtValue, rptEvtVldty, rptEvtDateTime, rptEvtObjType, rptEvtParaLen, rptEvtPara}
        STATUS current
        DESCRIPTION
        "Trap of PerEvt: ODU3_TCM4_FEUAS"
        ::= { optixTrapsPER  14761 }

--  1.3.6.1.4.1.2011.2.25.3.40.40.30.14762
    perEvtOdu3Tcm4Fesesr NOTIFICATION-TYPE
        OBJECTS { rptEvtPeriod, rptEvtValue, rptEvtVldty, rptEvtDateTime, rptEvtObjType, rptEvtParaLen, rptEvtPara}
        STATUS current
        DESCRIPTION
        "Trap of PerEvt: ODU3_TCM4_FESESR"
        ::= { optixTrapsPER  14762 }

--  1.3.6.1.4.1.2011.2.25.3.40.40.30.14763
    perEvtOdu3Tcm4Febber NOTIFICATION-TYPE
        OBJECTS { rptEvtPeriod, rptEvtValue, rptEvtVldty, rptEvtDateTime, rptEvtObjType, rptEvtParaLen, rptEvtPara}
        STATUS current
        DESCRIPTION
        "Trap of PerEvt: ODU3_TCM4_FEBBER"
        ::= { optixTrapsPER  14763 }

--  1.3.6.1.4.1.2011.2.25.3.40.40.30.14764
    perEvtOdu3Tcm5Febbe NOTIFICATION-TYPE
        OBJECTS { rptEvtPeriod, rptEvtValue, rptEvtVldty, rptEvtDateTime, rptEvtObjType, rptEvtParaLen, rptEvtPara}
        STATUS current
        DESCRIPTION
        "Trap of PerEvt: ODU3_TCM5_FEBBE"
        ::= { optixTrapsPER  14764 }

--  1.3.6.1.4.1.2011.2.25.3.40.40.30.14765
    perEvtOdu3Tcm5Fees NOTIFICATION-TYPE
        OBJECTS { rptEvtPeriod, rptEvtValue, rptEvtVldty, rptEvtDateTime, rptEvtObjType, rptEvtParaLen, rptEvtPara}
        STATUS current
        DESCRIPTION
        "Trap of PerEvt: ODU3_TCM5_FEES"
        ::= { optixTrapsPER  14765 }

--  1.3.6.1.4.1.2011.2.25.3.40.40.30.14766
    perEvtOdu3Tcm5Feses NOTIFICATION-TYPE
        OBJECTS { rptEvtPeriod, rptEvtValue, rptEvtVldty, rptEvtDateTime, rptEvtObjType, rptEvtParaLen, rptEvtPara}
        STATUS current
        DESCRIPTION
        "Trap of PerEvt: ODU3_TCM5_FESES"
        ::= { optixTrapsPER  14766 }

--  1.3.6.1.4.1.2011.2.25.3.40.40.30.14767
    perEvtOdu3Tcm5Feuas NOTIFICATION-TYPE
        OBJECTS { rptEvtPeriod, rptEvtValue, rptEvtVldty, rptEvtDateTime, rptEvtObjType, rptEvtParaLen, rptEvtPara}
        STATUS current
        DESCRIPTION
        "Trap of PerEvt: ODU3_TCM5_FEUAS"
        ::= { optixTrapsPER  14767 }

--  1.3.6.1.4.1.2011.2.25.3.40.40.30.14768
    perEvtOdu3Tcm5Fesesr NOTIFICATION-TYPE
        OBJECTS { rptEvtPeriod, rptEvtValue, rptEvtVldty, rptEvtDateTime, rptEvtObjType, rptEvtParaLen, rptEvtPara}
        STATUS current
        DESCRIPTION
        "Trap of PerEvt: ODU3_TCM5_FESESR"
        ::= { optixTrapsPER  14768 }

--  1.3.6.1.4.1.2011.2.25.3.40.40.30.14769
    perEvtOdu3Tcm5Febber NOTIFICATION-TYPE
        OBJECTS { rptEvtPeriod, rptEvtValue, rptEvtVldty, rptEvtDateTime, rptEvtObjType, rptEvtParaLen, rptEvtPara}
        STATUS current
        DESCRIPTION
        "Trap of PerEvt: ODU3_TCM5_FEBBER"
        ::= { optixTrapsPER  14769 }

--  1.3.6.1.4.1.2011.2.25.3.40.40.30.14770
    perEvtOdu3Tcm6Febbe NOTIFICATION-TYPE
        OBJECTS { rptEvtPeriod, rptEvtValue, rptEvtVldty, rptEvtDateTime, rptEvtObjType, rptEvtParaLen, rptEvtPara}
        STATUS current
        DESCRIPTION
        "Trap of PerEvt: ODU3_TCM6_FEBBE"
        ::= { optixTrapsPER  14770 }

--  1.3.6.1.4.1.2011.2.25.3.40.40.30.14771
    perEvtOdu3Tcm6Fees NOTIFICATION-TYPE
        OBJECTS { rptEvtPeriod, rptEvtValue, rptEvtVldty, rptEvtDateTime, rptEvtObjType, rptEvtParaLen, rptEvtPara}
        STATUS current
        DESCRIPTION
        "Trap of PerEvt: ODU3_TCM6_FEES"
        ::= { optixTrapsPER  14771 }

--  1.3.6.1.4.1.2011.2.25.3.40.40.30.14772
    perEvtOdu3Tcm6Feses NOTIFICATION-TYPE
        OBJECTS { rptEvtPeriod, rptEvtValue, rptEvtVldty, rptEvtDateTime, rptEvtObjType, rptEvtParaLen, rptEvtPara}
        STATUS current
        DESCRIPTION
        "Trap of PerEvt: ODU3_TCM6_FESES"
        ::= { optixTrapsPER  14772 }

--  1.3.6.1.4.1.2011.2.25.3.40.40.30.14773
    perEvtOdu3Tcm6Feuas NOTIFICATION-TYPE
        OBJECTS { rptEvtPeriod, rptEvtValue, rptEvtVldty, rptEvtDateTime, rptEvtObjType, rptEvtParaLen, rptEvtPara}
        STATUS current
        DESCRIPTION
        "Trap of PerEvt: ODU3_TCM6_FEUAS"
        ::= { optixTrapsPER  14773 }

--  1.3.6.1.4.1.2011.2.25.3.40.40.30.14774
    perEvtOdu3Tcm6Fesesr NOTIFICATION-TYPE
        OBJECTS { rptEvtPeriod, rptEvtValue, rptEvtVldty, rptEvtDateTime, rptEvtObjType, rptEvtParaLen, rptEvtPara}
        STATUS current
        DESCRIPTION
        "Trap of PerEvt: ODU3_TCM6_FESESR"
        ::= { optixTrapsPER  14774 }

--  1.3.6.1.4.1.2011.2.25.3.40.40.30.14775
    perEvtOdu3Tcm6Febber NOTIFICATION-TYPE
        OBJECTS { rptEvtPeriod, rptEvtValue, rptEvtVldty, rptEvtDateTime, rptEvtObjType, rptEvtParaLen, rptEvtPara}
        STATUS current
        DESCRIPTION
        "Trap of PerEvt: ODU3_TCM6_FEBBER"
        ::= { optixTrapsPER  14775 }

--  1.3.6.1.4.1.2011.2.25.3.40.40.30.14915
    perEvtCpTelDownCount NOTIFICATION-TYPE
        OBJECTS { rptEvtPeriod, rptEvtValue, rptEvtVldty, rptEvtDateTime, rptEvtObjType, rptEvtParaLen, rptEvtPara}
        STATUS current
        DESCRIPTION
        "Trap of PerEvt: CP_TEL_DOWN_COUNT"
        ::= { optixTrapsPER  14915 }

--  1.3.6.1.4.1.2011.2.25.3.40.40.30.14916
    perEvtCpTelDownTime NOTIFICATION-TYPE
        OBJECTS { rptEvtPeriod, rptEvtValue, rptEvtVldty, rptEvtDateTime, rptEvtObjType, rptEvtParaLen, rptEvtPara}
        STATUS current
        DESCRIPTION
        "Trap of PerEvt: CP_TEL_DOWN_TIME"
        ::= { optixTrapsPER  14916 }

--  1.3.6.1.4.1.2011.2.25.3.40.40.30.14917
    perEvtCpCcDownCount NOTIFICATION-TYPE
        OBJECTS { rptEvtPeriod, rptEvtValue, rptEvtVldty, rptEvtDateTime, rptEvtObjType, rptEvtParaLen, rptEvtPara}
        STATUS current
        DESCRIPTION
        "Trap of PerEvt: CP_CC_DOWN_COUNT"
        ::= { optixTrapsPER  14917 }

--  1.3.6.1.4.1.2011.2.25.3.40.40.30.14918
    perEvtCpCcDownTime NOTIFICATION-TYPE
        OBJECTS { rptEvtPeriod, rptEvtValue, rptEvtVldty, rptEvtDateTime, rptEvtObjType, rptEvtParaLen, rptEvtPara}
        STATUS current
        DESCRIPTION
        "Trap of PerEvt: CP_CC_DOWN_TIME"
        ::= { optixTrapsPER  14918 }


--  1.3.6.1.4.1.2011.2.25.3.40.40.30.14991
    perEvtBdtempmax NOTIFICATION-TYPE
        OBJECTS { rptEvtPeriod, rptEvtValue, rptEvtVldty, rptEvtDateTime, rptEvtObjType, rptEvtParaLen, rptEvtPara}
        STATUS current
        DESCRIPTION
        "Trap of PerEvt: Maximum value of board temperature"
        ::= { optixTrapsPER  14991 }

--  1.3.6.1.4.1.2011.2.25.3.40.40.30.14992
    perEvtBdtempmin NOTIFICATION-TYPE
        OBJECTS { rptEvtPeriod, rptEvtValue, rptEvtVldty, rptEvtDateTime, rptEvtObjType, rptEvtParaLen, rptEvtPara}
        STATUS current
        DESCRIPTION
        "Trap of PerEvt: Minimum value of board temperature"
        ::= { optixTrapsPER  14992 }

--  1.3.6.1.4.1.2011.2.25.3.40.40.30.14993
    perEvtBdtempcur NOTIFICATION-TYPE
        OBJECTS { rptEvtPeriod, rptEvtValue, rptEvtVldty, rptEvtDateTime, rptEvtObjType, rptEvtParaLen, rptEvtPara}
        STATUS current
        DESCRIPTION
        "Trap of PerEvt: Current value of board temperature"
        ::= { optixTrapsPER  14993 }

--  1.3.6.1.4.1.2011.2.25.3.40.40.30.15054
    perEvtOdu0PmBbe NOTIFICATION-TYPE
        OBJECTS { rptEvtPeriod, rptEvtValue, rptEvtVldty, rptEvtDateTime, rptEvtObjType, rptEvtParaLen, rptEvtPara}
        STATUS current
        DESCRIPTION
        "Trap of PerEvt: ODU PM Section Background Block Error"
        ::= { optixTrapsPER  15054 }

--  1.3.6.1.4.1.2011.2.25.3.40.40.30.15055
    perEvtOdu0PmEs NOTIFICATION-TYPE
        OBJECTS { rptEvtPeriod, rptEvtValue, rptEvtVldty, rptEvtDateTime, rptEvtObjType, rptEvtParaLen, rptEvtPara}
        STATUS current
        DESCRIPTION
        "Trap of PerEvt: ODU PM Section Errored Second"
        ::= { optixTrapsPER  15055 }

--  1.3.6.1.4.1.2011.2.25.3.40.40.30.15056
    perEvtOdu0PmSes NOTIFICATION-TYPE
        OBJECTS { rptEvtPeriod, rptEvtValue, rptEvtVldty, rptEvtDateTime, rptEvtObjType, rptEvtParaLen, rptEvtPara}
        STATUS current
        DESCRIPTION
        "Trap of PerEvt: ODU PM Section Severely Errored Second"
        ::= { optixTrapsPER  15056 }

--  1.3.6.1.4.1.2011.2.25.3.40.40.30.15057
    perEvtOdu0PmUas NOTIFICATION-TYPE
        OBJECTS { rptEvtPeriod, rptEvtValue, rptEvtVldty, rptEvtDateTime, rptEvtObjType, rptEvtParaLen, rptEvtPara}
        STATUS current
        DESCRIPTION
        "Trap of PerEvt: ODU PM Section Unavailable Second"
        ::= { optixTrapsPER  15057 }

--  1.3.6.1.4.1.2011.2.25.3.40.40.30.15058
    perEvtOdu0PmSesr NOTIFICATION-TYPE
        OBJECTS { rptEvtPeriod, rptEvtValue, rptEvtVldty, rptEvtDateTime, rptEvtObjType, rptEvtParaLen, rptEvtPara}
        STATUS current
        DESCRIPTION
        "Trap of PerEvt: ODU PM Section Ratio of Severely Errored Second"
        ::= { optixTrapsPER  15058 }

--  1.3.6.1.4.1.2011.2.25.3.40.40.30.15059
    perEvtOdu0PmBber NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Ratio of Background Block Error"
        ::= { optixTrapsPER  15059 }

--  1.3.6.1.4.1.2011.2.25.3.40.40.30.15060
    perEvtOdu0PmFebbe NOTIFICATION-TYPE
        OBJECTS { rptEvtPeriod, rptEvtValue, rptEvtVldty, rptEvtDateTime, rptEvtObjType, rptEvtParaLen, rptEvtPara}
        STATUS current
        DESCRIPTION
        "Trap of PerEvt: ODU PM Section Far End Background Block Error"
        ::= { optixTrapsPER  15060 }

--  1.3.6.1.4.1.2011.2.25.3.40.40.30.15061
    perEvtOdu0PmFees NOTIFICATION-TYPE
        OBJECTS { rptEvtPeriod, rptEvtValue, rptEvtVldty, rptEvtDateTime, rptEvtObjType, rptEvtParaLen, rptEvtPara}
        STATUS current
        DESCRIPTION
        "Trap of PerEvt: ODU PM Section Far End Background Block Error"
        ::= { optixTrapsPER  15061 }

--  1.3.6.1.4.1.2011.2.25.3.40.40.30.15062
    perEvtOdu0PmFeses NOTIFICATION-TYPE
        OBJECTS { rptEvtPeriod, rptEvtValue, rptEvtVldty, rptEvtDateTime, rptEvtObjType, rptEvtParaLen, rptEvtPara}
        STATUS current
        DESCRIPTION
        "Trap of PerEvt: ODU PM Section Far End Severely Errored Second"
        ::= { optixTrapsPER  15062 }

--  1.3.6.1.4.1.2011.2.25.3.40.40.30.15063
    perEvtOdu0PmFeuas NOTIFICATION-TYPE
        OBJECTS { rptEvtPeriod, rptEvtValue, rptEvtVldty, rptEvtDateTime, rptEvtObjType, rptEvtParaLen, rptEvtPara}
        STATUS current
        DESCRIPTION
        "Trap of PerEvt: ODU PM Section Unavailable Second"
        ::= { optixTrapsPER  15063 }

--  1.3.6.1.4.1.2011.2.25.3.40.40.30.15064
    perEvtOdu0PmFesesr NOTIFICATION-TYPE
        OBJECTS { rptEvtPeriod, rptEvtValue, rptEvtVldty, rptEvtDateTime, rptEvtObjType, rptEvtParaLen, rptEvtPara}
        STATUS current
        DESCRIPTION
        "Trap of PerEvt: ODU PM Section Ratio of Far End Severely Errored Second"
        ::= { optixTrapsPER  15064 }

--  1.3.6.1.4.1.2011.2.25.3.40.40.30.15065
    perEvtOdu0PmFebber NOTIFICATION-TYPE
        OBJECTS { rptEvtPeriod, rptEvtValue, rptEvtVldty, rptEvtDateTime, rptEvtObjType, rptEvtParaLen, rptEvtPara}
        STATUS current
        DESCRIPTION
        "Trap of PerEvt: ODU PM Section Ratio of Far End Background Block Error"
        ::= { optixTrapsPER  15065 }

--  1.3.6.1.4.1.2011.2.25.3.40.40.30.15088
    perEvtMaxfreqdev NOTIFICATION-TYPE
        OBJECTS { rptEvtPeriod, rptEvtValue, rptEvtVldty, rptEvtDateTime, rptEvtObjType, rptEvtParaLen, rptEvtPara}
        STATUS current
        DESCRIPTION
        "Trap of PerEvt: Maximum frequency deviation from the output clock and the reference clock source for the input clock"
        ::= { optixTrapsPER  15088 }

--  1.3.6.1.4.1.2011.2.25.3.40.40.30.15089
    perEvtMinfreqdev NOTIFICATION-TYPE
        OBJECTS { rptEvtPeriod, rptEvtValue, rptEvtVldty, rptEvtDateTime, rptEvtObjType, rptEvtParaLen, rptEvtPara}
        STATUS current
        DESCRIPTION
        "Trap of PerEvt: Minimum frequency deviation from the output clock and the reference clock source for the input clock"
        ::= { optixTrapsPER  15089 }

--  1.3.6.1.4.1.2011.2.25.3.40.40.30.15090
    perEvtAvgfreqdev NOTIFICATION-TYPE
        OBJECTS { rptEvtPeriod, rptEvtValue, rptEvtVldty, rptEvtDateTime, rptEvtObjType, rptEvtParaLen, rptEvtPara}
        STATUS current
        DESCRIPTION
        "Trap of PerEvt: Average frequency deviation from the output clock and the reference clock source for the input clock"
        ::= { optixTrapsPER  15090 }

--  1.3.6.1.4.1.2011.2.25.3.40.40.30.15091
    perEvtMaxphaseoffset NOTIFICATION-TYPE
        OBJECTS { rptEvtPeriod, rptEvtValue, rptEvtVldty, rptEvtDateTime, rptEvtObjType, rptEvtParaLen, rptEvtPara}
        STATUS current
        DESCRIPTION
        "Trap of PerEvt: Maximum phase offset between the master clock and slave clock"
        ::= { optixTrapsPER  15091 }

--  1.3.6.1.4.1.2011.2.25.3.40.40.30.15092
    perEvtMinphaseoffset NOTIFICATION-TYPE
        OBJECTS { rptEvtPeriod, rptEvtValue, rptEvtVldty, rptEvtDateTime, rptEvtObjType, rptEvtParaLen, rptEvtPara}
        STATUS current
        DESCRIPTION
        "Trap of PerEvt: Minimum phase offset between the master clock and slave clock"
        ::= { optixTrapsPER  15092 }

--  1.3.6.1.4.1.2011.2.25.3.40.40.30.15093
    perEvtAvgphaseoffset NOTIFICATION-TYPE
        OBJECTS { rptEvtPeriod, rptEvtValue, rptEvtVldty, rptEvtDateTime, rptEvtObjType, rptEvtParaLen, rptEvtPara}
        STATUS current
        DESCRIPTION
        "Trap of PerEvt: Average phase offset between the master clock and slave clock"
        ::= { optixTrapsPER  15093 }

--  1.3.6.1.4.1.2011.2.25.3.40.40.30.15094
    perEvtMaxmeanpathdelay NOTIFICATION-TYPE
        OBJECTS { rptEvtPeriod, rptEvtValue, rptEvtVldty, rptEvtDateTime, rptEvtObjType, rptEvtParaLen, rptEvtPara}
        STATUS current
        DESCRIPTION
        "Trap of PerEvt: Maximum path delay between the master clock and slave clock"
        ::= { optixTrapsPER  15094 }

--  1.3.6.1.4.1.2011.2.25.3.40.40.30.15095
    perEvtMinmeanpathdelay NOTIFICATION-TYPE
        OBJECTS { rptEvtPeriod, rptEvtValue, rptEvtVldty, rptEvtDateTime, rptEvtObjType, rptEvtParaLen, rptEvtPara}
        STATUS current
        DESCRIPTION
        "Trap of PerEvt: Minimum path delay between the master clock and slave clock"
        ::= { optixTrapsPER  15095 }

--  1.3.6.1.4.1.2011.2.25.3.40.40.30.15096
    perEvtAvgmeanpathdelay NOTIFICATION-TYPE
        OBJECTS { rptEvtPeriod, rptEvtValue, rptEvtVldty, rptEvtDateTime, rptEvtObjType, rptEvtParaLen, rptEvtPara}
        STATUS current
        DESCRIPTION
        "Trap of PerEvt: Average path delay between the master clock and slave clock"
        ::= { optixTrapsPER  15096 }

--  1.3.6.1.4.1.2011.2.25.3.40.40.30.15103
    perEvtMaxpositivedelay NOTIFICATION-TYPE
        OBJECTS { rptEvtPeriod, rptEvtValue, rptEvtVldty, rptEvtDateTime, rptEvtObjType, rptEvtParaLen, rptEvtPara}
        STATUS current
        DESCRIPTION
        "Trap of PerEvt: Maximum positive delay between the master clock and slave clock"
        ::= { optixTrapsPER  15103 }

--  1.3.6.1.4.1.2011.2.25.3.40.40.30.15104
    perEvtMinpositivedelay NOTIFICATION-TYPE
        OBJECTS { rptEvtPeriod, rptEvtValue, rptEvtVldty, rptEvtDateTime, rptEvtObjType, rptEvtParaLen, rptEvtPara}
        STATUS current
        DESCRIPTION
        "Trap of PerEvt: Minimum positive delay between the master clock and slave clock"
        ::= { optixTrapsPER  15104 }

--  1.3.6.1.4.1.2011.2.25.3.40.40.30.15105
    perEvtAvgpositivedelay NOTIFICATION-TYPE
        OBJECTS { rptEvtPeriod, rptEvtValue, rptEvtVldty, rptEvtDateTime, rptEvtObjType, rptEvtParaLen, rptEvtPara}
        STATUS current
        DESCRIPTION
        "Trap of PerEvt: Average positive delay between the master clock and slave clock"
        ::= { optixTrapsPER  15105 }

--  1.3.6.1.4.1.2011.2.25.3.40.40.30.15106
    perEvtMaxnegativedelay NOTIFICATION-TYPE
        OBJECTS { rptEvtPeriod, rptEvtValue, rptEvtVldty, rptEvtDateTime, rptEvtObjType, rptEvtParaLen, rptEvtPara}
        STATUS current
        DESCRIPTION
        "Trap of PerEvt: Maximum negative delay between the master clock and slave clock"
        ::= { optixTrapsPER  15106 }

--  1.3.6.1.4.1.2011.2.25.3.40.40.30.15107
    perEvtMinnegativedelay NOTIFICATION-TYPE
        OBJECTS { rptEvtPeriod, rptEvtValue, rptEvtVldty, rptEvtDateTime, rptEvtObjType, rptEvtParaLen, rptEvtPara}
        STATUS current
        DESCRIPTION
        "Trap of PerEvt: Minimum negative delay between the master clock and slave clock"
        ::= { optixTrapsPER  15107 }

--  1.3.6.1.4.1.2011.2.25.3.40.40.30.15108
    perEvtAvgnegativedelay NOTIFICATION-TYPE
        OBJECTS { rptEvtPeriod, rptEvtValue, rptEvtVldty, rptEvtDateTime, rptEvtObjType, rptEvtParaLen, rptEvtPara}
        STATUS current
        DESCRIPTION
        "Trap of PerEvt: Average negative delay between the master clock and slave clock"
        ::= { optixTrapsPER  15108 }

--  1.3.6.1.4.1.2011.2.25.3.40.40.30.15135
    perEvtOdu4Tcm1Iaes NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Incoming Alignment Errored Second"
        ::= { optixTrapsPER  15135 }

--  1.3.6.1.4.1.2011.2.25.3.40.40.30.15136
    perEvtOdu4Tcm2Iaes NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Incoming Alignment Errored Second"
        ::= { optixTrapsPER  15136 }

--  1.3.6.1.4.1.2011.2.25.3.40.40.30.15137
    perEvtOdu4Tcm3Iaes NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Incoming Alignment Errored Second"
        ::= { optixTrapsPER  15137 }

--  1.3.6.1.4.1.2011.2.25.3.40.40.30.15138
    perEvtOdu4Tcm4Iaes NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Incoming Alignment Errored Second"
        ::= { optixTrapsPER  15138 }

--  1.3.6.1.4.1.2011.2.25.3.40.40.30.15139
    perEvtOdu4Tcm5Iaes NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Incoming Alignment Errored Second"
        ::= { optixTrapsPER  15139 }

--  1.3.6.1.4.1.2011.2.25.3.40.40.30.15140
    perEvtOdu4Tcm6Iaes NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Incoming Alignment Errored Second"
        ::= { optixTrapsPER  15140 }

--  1.3.6.1.4.1.2011.2.25.3.40.40.30.15141
    perEvtOdu4Tcm1Biaes NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Backward Incoming Alignment Errored Second"
        ::= { optixTrapsPER  15141 }

--  1.3.6.1.4.1.2011.2.25.3.40.40.30.15142
    perEvtOdu4Tcm2Biaes NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Backward Incoming Alignment Errored Second"
        ::= { optixTrapsPER  15142 }

--  1.3.6.1.4.1.2011.2.25.3.40.40.30.15143
    perEvtOdu4Tcm3Biaes NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Backward Incoming Alignment Errored Second"
        ::= { optixTrapsPER  15143 }

--  1.3.6.1.4.1.2011.2.25.3.40.40.30.15144
    perEvtOdu4Tcm4Biaes NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Backward Incoming Alignment Errored Second"
        ::= { optixTrapsPER  15144 }

--  1.3.6.1.4.1.2011.2.25.3.40.40.30.15145
    perEvtOdu4Tcm5Biaes NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Backward Incoming Alignment Errored Second"
        ::= { optixTrapsPER  15145 }

--  1.3.6.1.4.1.2011.2.25.3.40.40.30.15146
    perEvtOdu4Tcm6Biaes NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Backward Incoming Alignment Errored Second"
        ::= { optixTrapsPER  15146 }

--  1.3.6.1.4.1.2011.2.25.3.40.40.30.15147
    perEvtOdu4Tcm1Bbe NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Background Block Error"
        ::= { optixTrapsPER  15147 }

--  1.3.6.1.4.1.2011.2.25.3.40.40.30.15148
    perEvtOdu4Tcm1Es NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Errored Second"
        ::= { optixTrapsPER  15148 }

--  1.3.6.1.4.1.2011.2.25.3.40.40.30.15149
    perEvtOdu4Tcm1Ses NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Severely Errored Second"
        ::= { optixTrapsPER  15149 }

--  1.3.6.1.4.1.2011.2.25.3.40.40.30.15150
    perEvtOdu4Tcm1Uas NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Unavailable Second"
        ::= { optixTrapsPER  15150 }

--  1.3.6.1.4.1.2011.2.25.3.40.40.30.15151
    perEvtOdu4Tcm1Sesr NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Ratio of Severely Errored Second"
        ::= { optixTrapsPER  15151 }

--  1.3.6.1.4.1.2011.2.25.3.40.40.30.15152
    perEvtOdu4Tcm1Bber NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Ratio of Background Block Error"
        ::= { optixTrapsPER  15152 }

--  1.3.6.1.4.1.2011.2.25.3.40.40.30.15153
    perEvtOdu4Tcm2Bbe NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Background Block Error"
        ::= { optixTrapsPER  15153 }

--  1.3.6.1.4.1.2011.2.25.3.40.40.30.15154
    perEvtOdu4Tcm2Es NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Errored Second"
        ::= { optixTrapsPER  15154 }

--  1.3.6.1.4.1.2011.2.25.3.40.40.30.15155
    perEvtOdu4Tcm2Ses NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Severely Errored Second"
        ::= { optixTrapsPER  15155 }

--  1.3.6.1.4.1.2011.2.25.3.40.40.30.15156
    perEvtOdu4Tcm2Uas NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Unavailable Second"
        ::= { optixTrapsPER  15156 }

--  1.3.6.1.4.1.2011.2.25.3.40.40.30.15157
    perEvtOdu4Tcm2Sesr NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Ratio of Severely Errored Second"
        ::= { optixTrapsPER  15157 }

--  1.3.6.1.4.1.2011.2.25.3.40.40.30.15158
    perEvtOdu4Tcm2Bber NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Ratio of Background Block Error"
        ::= { optixTrapsPER  15158 }

--  1.3.6.1.4.1.2011.2.25.3.40.40.30.15159
    perEvtOdu4Tcm3Bbe NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Background Block Error"
        ::= { optixTrapsPER  15159 }

--  1.3.6.1.4.1.2011.2.25.3.40.40.30.15160
    perEvtOdu4Tcm3Es NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Errored Second"
        ::= { optixTrapsPER  15160 }

--  1.3.6.1.4.1.2011.2.25.3.40.40.30.15161
    perEvtOdu4Tcm3Ses NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Severely Errored Second"
        ::= { optixTrapsPER  15161 }

--  1.3.6.1.4.1.2011.2.25.3.40.40.30.15162
    perEvtOdu4Tcm3Uas NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Unavailable Second"
        ::= { optixTrapsPER  15162 }

--  1.3.6.1.4.1.2011.2.25.3.40.40.30.15163
    perEvtOdu4Tcm3Sesr NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Ratio of Severely Errored Second"
        ::= { optixTrapsPER  15163 }

--  1.3.6.1.4.1.2011.2.25.3.40.40.30.15164
    perEvtOdu4Tcm3Bber NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Ratio of Background Block Error"
        ::= { optixTrapsPER  15164 }

--  1.3.6.1.4.1.2011.2.25.3.40.40.30.15165
    perEvtOdu4Tcm4Bbe NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Background Block Error"
        ::= { optixTrapsPER  15165 }

--  1.3.6.1.4.1.2011.2.25.3.40.40.30.15166
    perEvtOdu4Tcm4Es NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Errored Second"
        ::= { optixTrapsPER  15166 }

--  1.3.6.1.4.1.2011.2.25.3.40.40.30.15167
    perEvtOdu4Tcm4Ses NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Severely Errored Second"
        ::= { optixTrapsPER  15167 }

--  1.3.6.1.4.1.2011.2.25.3.40.40.30.15168
    perEvtOdu4Tcm4Uas NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Unavailable Second"
        ::= { optixTrapsPER  15168 }

--  1.3.6.1.4.1.2011.2.25.3.40.40.30.15169
    perEvtOdu4Tcm4Sesr NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Ratio of Severely Errored Second"
        ::= { optixTrapsPER  15169 }

--  1.3.6.1.4.1.2011.2.25.3.40.40.30.15170
    perEvtOdu4Tcm4Bber NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Ratio of Background Block Error"
        ::= { optixTrapsPER  15170 }

--  1.3.6.1.4.1.2011.2.25.3.40.40.30.15171
    perEvtOdu4Tcm5Bbe NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Background Block Error"
        ::= { optixTrapsPER  15171 }

--  1.3.6.1.4.1.2011.2.25.3.40.40.30.15172
    perEvtOdu4Tcm5Es NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Errored Second"
        ::= { optixTrapsPER  15172 }

--  1.3.6.1.4.1.2011.2.25.3.40.40.30.15173
    perEvtOdu4Tcm5Ses NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Severely Errored Second"
        ::= { optixTrapsPER  15173 }

--  1.3.6.1.4.1.2011.2.25.3.40.40.30.15174
    perEvtOdu4Tcm5Uas NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Unavailable Second"
        ::= { optixTrapsPER  15174 }

--  1.3.6.1.4.1.2011.2.25.3.40.40.30.15175
    perEvtOdu4Tcm5Sesr NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Ratio of Severely Errored Second"
        ::= { optixTrapsPER  15175 }

--  1.3.6.1.4.1.2011.2.25.3.40.40.30.15176
    perEvtOdu4Tcm5Bber NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Ratio of Background Block Error"
        ::= { optixTrapsPER  15176 }

--  1.3.6.1.4.1.2011.2.25.3.40.40.30.15177
    perEvtOdu4Tcm6Bbe NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Background Block Error"
        ::= { optixTrapsPER  15177 }

--  1.3.6.1.4.1.2011.2.25.3.40.40.30.15178
    perEvtOdu4Tcm6Es NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Errored Second"
        ::= { optixTrapsPER  15178 }

--  1.3.6.1.4.1.2011.2.25.3.40.40.30.15179
    perEvtOdu4Tcm6Ses NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Severely Errored Second"
        ::= { optixTrapsPER  15179 }

--  1.3.6.1.4.1.2011.2.25.3.40.40.30.15180
    perEvtOdu4Tcm6Uas NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Unavailable Second"
        ::= { optixTrapsPER  15180 }

--  1.3.6.1.4.1.2011.2.25.3.40.40.30.15181
    perEvtOdu4Tcm6Sesr NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Ratio of Severely Errored Second"
        ::= { optixTrapsPER  15181 }

--  1.3.6.1.4.1.2011.2.25.3.40.40.30.15182
    perEvtOdu4Tcm6Bber NOTIFICATION-TYPE
        OBJECTS { rptEvtPeriod, rptEvtValue, rptEvtVldty, rptEvtDateTime, rptEvtObjType, rptEvtParaLen, rptEvtPara}
        STATUS current
        DESCRIPTION
        "Trap of PerEvt: ODUk TCMn Section Ratio of Background Block Error"
        ::= { optixTrapsPER  15182 }

--  1.3.6.1.4.1.2011.2.25.3.40.40.30.15183
    perEvtOdu4Tcm1Febbe NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Far End Background Block Error"
        ::= { optixTrapsPER  15183 }

--  1.3.6.1.4.1.2011.2.25.3.40.40.30.15184
    perEvtOdu4Tcm1Fees NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Far End Background Block Error"
        ::= { optixTrapsPER  15184 }

--  1.3.6.1.4.1.2011.2.25.3.40.40.30.15185
    perEvtOdu4Tcm1Feses NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Far End Severely Errored Second"
        ::= { optixTrapsPER  15185 }

--  1.3.6.1.4.1.2011.2.25.3.40.40.30.15186
    perEvtOdu4Tcm1Feuas NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Unavailable Second"
        ::= { optixTrapsPER  15186 }

--  1.3.6.1.4.1.2011.2.25.3.40.40.30.15187
    perEvtOdu4Tcm1Fesesr NOTIFICATION-TYPE
        OBJECTS { rptEvtPeriod, rptEvtValue, rptEvtVldty, rptEvtDateTime, rptEvtObjType, rptEvtParaLen, rptEvtPara}
        STATUS current
        DESCRIPTION
        "Trap of PerEvt: OTUk TCMn  Section Ratio of Far End Severely Errored Second"
        ::= { optixTrapsPER  15187 }

--  1.3.6.1.4.1.2011.2.25.3.40.40.30.15188
    perEvtOdu4Tcm1Febber NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Ratio of Far End Background Block Error"
        ::= { optixTrapsPER  15188 }

--  1.3.6.1.4.1.2011.2.25.3.40.40.30.15189
    perEvtOdu4Tcm2Febbe NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Far End Background Block Error"
        ::= { optixTrapsPER  15189 }

--  1.3.6.1.4.1.2011.2.25.3.40.40.30.15190
    perEvtOdu4Tcm2Fees NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Far End Background Block Error"
        ::= { optixTrapsPER  15190 }

--  1.3.6.1.4.1.2011.2.25.3.40.40.30.15191
    perEvtOdu4Tcm2Feses NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Far End Severely Errored Second"
        ::= { optixTrapsPER  15191 }

--  1.3.6.1.4.1.2011.2.25.3.40.40.30.15192
    perEvtOdu4Tcm2Feuas NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Unavailable Second"
        ::= { optixTrapsPER  15192 }

--  1.3.6.1.4.1.2011.2.25.3.40.40.30.15193
    perEvtOdu4Tcm2Fesesr NOTIFICATION-TYPE
        OBJECTS { rptEvtPeriod, rptEvtValue, rptEvtVldty, rptEvtDateTime, rptEvtObjType, rptEvtParaLen, rptEvtPara}
        STATUS current
        DESCRIPTION
        "Trap of PerEvt: OTUk TCMn  Section Ratio of Far End Severely Errored Second"
        ::= { optixTrapsPER  15193 }

--  1.3.6.1.4.1.2011.2.25.3.40.40.30.15194
    perEvtOdu4Tcm2Febber NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Ratio of Far End Background Block Error"
        ::= { optixTrapsPER  15194 }

--  1.3.6.1.4.1.2011.2.25.3.40.40.30.15195
    perEvtOdu4Tcm3Febbe NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Far End Background Block Error"
        ::= { optixTrapsPER  15195 }

--  1.3.6.1.4.1.2011.2.25.3.40.40.30.15196
    perEvtOdu4Tcm3Fees NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Far End Background Block Error"
        ::= { optixTrapsPER  15196 }

--  1.3.6.1.4.1.2011.2.25.3.40.40.30.15197
    perEvtOdu4Tcm3Feses NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Far End Severely Errored Second"
        ::= { optixTrapsPER  15197 }

--  1.3.6.1.4.1.2011.2.25.3.40.40.30.15198
    perEvtOdu4Tcm3Feuas NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Unavailable Second"
        ::= { optixTrapsPER  15198 }

--  1.3.6.1.4.1.2011.2.25.3.40.40.30.15199
    perEvtOdu4Tcm3Fesesr NOTIFICATION-TYPE
        OBJECTS { rptEvtPeriod, rptEvtValue, rptEvtVldty, rptEvtDateTime, rptEvtObjType, rptEvtParaLen, rptEvtPara}
        STATUS current
        DESCRIPTION
        "Trap of PerEvt: OTUk TCMn  Section Ratio of Far End Severely Errored Second"
        ::= { optixTrapsPER  15199 }

--  1.3.6.1.4.1.2011.2.25.3.40.40.30.15200
    perEvtOdu4Tcm3Febber NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Ratio of Far End Background Block Error"
        ::= { optixTrapsPER  15200 }

--  1.3.6.1.4.1.2011.2.25.3.40.40.30.15201
    perEvtOdu4Tcm4Febbe NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Far End Background Block Error"
        ::= { optixTrapsPER  15201 }

--  1.3.6.1.4.1.2011.2.25.3.40.40.30.15202
    perEvtOdu4Tcm4Fees NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Far End Background Block Error"
        ::= { optixTrapsPER  15202 }

--  1.3.6.1.4.1.2011.2.25.3.40.40.30.15203
    perEvtOdu4Tcm4Feses NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Far End Severely Errored Second"
        ::= { optixTrapsPER  15203 }

--  1.3.6.1.4.1.2011.2.25.3.40.40.30.15204
    perEvtOdu4Tcm4Feuas NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Unavailable Second"
        ::= { optixTrapsPER  15204 }

--  1.3.6.1.4.1.2011.2.25.3.40.40.30.15205
    perEvtOdu4Tcm4Fesesr NOTIFICATION-TYPE
        OBJECTS { rptEvtPeriod, rptEvtValue, rptEvtVldty, rptEvtDateTime, rptEvtObjType, rptEvtParaLen, rptEvtPara}
        STATUS current
        DESCRIPTION
        "Trap of PerEvt: OTUk TCMn  Section Ratio of Far End Severely Errored Second"
        ::= { optixTrapsPER  15205 }

--  1.3.6.1.4.1.2011.2.25.3.40.40.30.15206
    perEvtOdu4Tcm4Febber NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Ratio of Far End Background Block Error"
        ::= { optixTrapsPER  15206 }

--  1.3.6.1.4.1.2011.2.25.3.40.40.30.15207
    perEvtOdu4Tcm5Febbe NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Far End Background Block Error"
        ::= { optixTrapsPER  15207 }

--  1.3.6.1.4.1.2011.2.25.3.40.40.30.15208
    perEvtOdu4Tcm5Fees NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Far End Background Block Error"
        ::= { optixTrapsPER  15208 }

--  1.3.6.1.4.1.2011.2.25.3.40.40.30.15209
    perEvtOdu4Tcm5Feses NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Far End Severely Errored Second"
        ::= { optixTrapsPER  15209 }

--  1.3.6.1.4.1.2011.2.25.3.40.40.30.15210
    perEvtOdu4Tcm5Feuas NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Unavailable Second"
        ::= { optixTrapsPER  15210 }

--  1.3.6.1.4.1.2011.2.25.3.40.40.30.15211
    perEvtOdu4Tcm5Fesesr NOTIFICATION-TYPE
        OBJECTS { rptEvtPeriod, rptEvtValue, rptEvtVldty, rptEvtDateTime, rptEvtObjType, rptEvtParaLen, rptEvtPara}
        STATUS current
        DESCRIPTION
        "Trap of PerEvt: OTUk TCMn  Section Ratio of Far End Severely Errored Second"
        ::= { optixTrapsPER  15211 }

--  1.3.6.1.4.1.2011.2.25.3.40.40.30.15212
    perEvtOdu4Tcm5Febber NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Ratio of Far End Background Block Error"
        ::= { optixTrapsPER  15212 }

--  1.3.6.1.4.1.2011.2.25.3.40.40.30.15213
    perEvtOdu4Tcm6Febbe NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Far End Background Block Error"
        ::= { optixTrapsPER  15213 }

--  1.3.6.1.4.1.2011.2.25.3.40.40.30.15214
    perEvtOdu4Tcm6Fees NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Far End Background Block Error"
        ::= { optixTrapsPER  15214 }

--  1.3.6.1.4.1.2011.2.25.3.40.40.30.15215
    perEvtOdu4Tcm6Feses NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Far End Severely Errored Second"
        ::= { optixTrapsPER  15215 }

--  1.3.6.1.4.1.2011.2.25.3.40.40.30.15216
    perEvtOdu4Tcm6Feuas NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Unavailable Second"
        ::= { optixTrapsPER  15216 }

--  1.3.6.1.4.1.2011.2.25.3.40.40.30.15217
    perEvtOdu4Tcm6Fesesr NOTIFICATION-TYPE
        OBJECTS { rptEvtPeriod, rptEvtValue, rptEvtVldty, rptEvtDateTime, rptEvtObjType, rptEvtParaLen, rptEvtPara}
        STATUS current
        DESCRIPTION
        "Trap of PerEvt: OTUk TCMn  Section Ratio of Far End Severely Errored Second"
        ::= { optixTrapsPER  15217 }

--  1.3.6.1.4.1.2011.2.25.3.40.40.30.15218
    perEvtOdu4Tcm6Febber NOTIFICATION-TYPE
        OBJECTS { rptEvtPeriod, rptEvtValue, rptEvtVldty, rptEvtDateTime, rptEvtObjType, rptEvtParaLen, rptEvtPara}
        STATUS current
        DESCRIPTION
        "Trap of PerEvt: OTUk TCMn Section Ratio of Far End Background Block Error"
        ::= { optixTrapsPER  15218 }

--  1.3.6.1.4.1.2011.2.25.3.40.40.30.15267
    perEvtOduflexPmBbe NOTIFICATION-TYPE
        OBJECTS { rptEvtPeriod, rptEvtValue, rptEvtVldty, rptEvtDateTime, rptEvtObjType, rptEvtParaLen, rptEvtPara}
        STATUS current
        DESCRIPTION
        "Trap of PerEvt: ODUFLEX PM Section Background Block Error"
        ::= { optixTrapsPER  15267 }

--  1.3.6.1.4.1.2011.2.25.3.40.40.30.15268
    perEvtOduflexPmEs NOTIFICATION-TYPE
        OBJECTS { rptEvtPeriod, rptEvtValue, rptEvtVldty, rptEvtDateTime, rptEvtObjType, rptEvtParaLen, rptEvtPara}
        STATUS current
        DESCRIPTION
        "Trap of PerEvt: ODUFLEX PM Section Errored Second"
        ::= { optixTrapsPER  15268 }

--  1.3.6.1.4.1.2011.2.25.3.40.40.30.15269
    perEvtOduflexPmSes NOTIFICATION-TYPE
        OBJECTS { rptEvtPeriod, rptEvtValue, rptEvtVldty, rptEvtDateTime, rptEvtObjType, rptEvtParaLen, rptEvtPara}
        STATUS current
        DESCRIPTION
        "Trap of PerEvt: ODUFLEX PM Section Severely Errored Second"
        ::= { optixTrapsPER  15269 }

--  1.3.6.1.4.1.2011.2.25.3.40.40.30.15270
    perEvtOduflexPmUas NOTIFICATION-TYPE
        OBJECTS { rptEvtPeriod, rptEvtValue, rptEvtVldty, rptEvtDateTime, rptEvtObjType, rptEvtParaLen, rptEvtPara}
        STATUS current
        DESCRIPTION
        "Trap of PerEvt: ODUFLEX PM Section Unavailable Second"
        ::= { optixTrapsPER  15270 }

--  1.3.6.1.4.1.2011.2.25.3.40.40.30.15271
    perEvtOduflexPmSesr NOTIFICATION-TYPE
        OBJECTS { rptEvtPeriod, rptEvtValue, rptEvtVldty, rptEvtDateTime, rptEvtObjType, rptEvtParaLen, rptEvtPara}
        STATUS current
        DESCRIPTION
        "Trap of PerEvt: ODUFLEX PM Section Ratio of Severely Errored Second"
        ::= { optixTrapsPER  15271 }

--  1.3.6.1.4.1.2011.2.25.3.40.40.30.15272
    perEvtOduflexPmBber NOTIFICATION-TYPE
        OBJECTS { rptEvtPeriod, rptEvtValue, rptEvtVldty, rptEvtDateTime, rptEvtObjType, rptEvtParaLen, rptEvtPara}
        STATUS current
        DESCRIPTION
        "Trap of PerEvt: ODUFLEX PM Section Ratio of Background Block Error"
        ::= { optixTrapsPER  15272 }

--  1.3.6.1.4.1.2011.2.25.3.40.40.30.15273
    perEvtOduflexPmFebbe NOTIFICATION-TYPE
        OBJECTS { rptEvtPeriod, rptEvtValue, rptEvtVldty, rptEvtDateTime, rptEvtObjType, rptEvtParaLen, rptEvtPara}
        STATUS current
        DESCRIPTION
        "Trap of PerEvt: ODUFLEX PM Section Far End Background Block Error"
        ::= { optixTrapsPER  15273 }

--  1.3.6.1.4.1.2011.2.25.3.40.40.30.15274
    perEvtOduflexPmFees NOTIFICATION-TYPE
        OBJECTS { rptEvtPeriod, rptEvtValue, rptEvtVldty, rptEvtDateTime, rptEvtObjType, rptEvtParaLen, rptEvtPara}
        STATUS current
        DESCRIPTION
        "Trap of PerEvt: ODUFLEX PM Section Far End Background Block Error"
        ::= { optixTrapsPER  15274 }

--  1.3.6.1.4.1.2011.2.25.3.40.40.30.15275
    perEvtOduflexPmFeses NOTIFICATION-TYPE
        OBJECTS { rptEvtPeriod, rptEvtValue, rptEvtVldty, rptEvtDateTime, rptEvtObjType, rptEvtParaLen, rptEvtPara}
        STATUS current
        DESCRIPTION
        "Trap of PerEvt: ODUFLEX PM Section Far End Severely Errored Second"
        ::= { optixTrapsPER  15275 }

--  1.3.6.1.4.1.2011.2.25.3.40.40.30.15276
    perEvtOduflexPmFeuas NOTIFICATION-TYPE
        OBJECTS { rptEvtPeriod, rptEvtValue, rptEvtVldty, rptEvtDateTime, rptEvtObjType, rptEvtParaLen, rptEvtPara}
        STATUS current
        DESCRIPTION
        "Trap of PerEvt: ODUFLEX PM Section Unavailable Second"
        ::= { optixTrapsPER  15276 }

--  1.3.6.1.4.1.2011.2.25.3.40.40.30.15277
    perEvtOduflexPmFesesr NOTIFICATION-TYPE
        OBJECTS { rptEvtPeriod, rptEvtValue, rptEvtVldty, rptEvtDateTime, rptEvtObjType, rptEvtParaLen, rptEvtPara}
        STATUS current
        DESCRIPTION
        "Trap of PerEvt: ODUFLEXPM Section Ratio of Far End Severely Errored Second"
        ::= { optixTrapsPER  15277 }

--  1.3.6.1.4.1.2011.2.25.3.40.40.30.15278
    perEvtOduflexPmFebber NOTIFICATION-TYPE
        OBJECTS { rptEvtPeriod, rptEvtValue, rptEvtVldty, rptEvtDateTime, rptEvtObjType, rptEvtParaLen, rptEvtPara}
        STATUS current
        DESCRIPTION
        "Trap of PerEvt: ODUFLEX PM Section Ratio of Far End Background Block Error"
        ::= { optixTrapsPER  15278 }

--  1.3.6.1.4.1.2011.2.25.3.40.40.30.15279
    perEvtOdu0Tcm1Bbe NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Background Block Error"
        ::= { optixTrapsPER  15279 }

--  1.3.6.1.4.1.2011.2.25.3.40.40.30.15280
    perEvtOdu0Tcm1Es NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Errored Second"
        ::= { optixTrapsPER  15280 }

--  1.3.6.1.4.1.2011.2.25.3.40.40.30.15281
    perEvtOdu0Tcm1Ses NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Severely Errored Second"
        ::= { optixTrapsPER  15281 }

--  1.3.6.1.4.1.2011.2.25.3.40.40.30.15282
    perEvtOdu0Tcm1Uas NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Unavailable Second"
        ::= { optixTrapsPER  15282 }

--  1.3.6.1.4.1.2011.2.25.3.40.40.30.15283
    perEvtOdu0Tcm1Sesr NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Ratio of Severely Errored Second"
        ::= { optixTrapsPER  15283 }

--  1.3.6.1.4.1.2011.2.25.3.40.40.30.15284
    perEvtOdu0Tcm1Bber NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Ratio of Background Block Error"
        ::= { optixTrapsPER  15284 }

--  1.3.6.1.4.1.2011.2.25.3.40.40.30.15285
    perEvtOdu0Tcm1Febbe NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Far End Background Block Error"
        ::= { optixTrapsPER  15285 }

--  1.3.6.1.4.1.2011.2.25.3.40.40.30.15286
    perEvtOdu0Tcm1Fees NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Far End Background Block Error"
        ::= { optixTrapsPER  15286 }

--  1.3.6.1.4.1.2011.2.25.3.40.40.30.15287
    perEvtOdu0Tcm1Feses NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Far End Severely Errored Second"
        ::= { optixTrapsPER  15287 }

--  1.3.6.1.4.1.2011.2.25.3.40.40.30.15288
    perEvtOdu0Tcm1Feuas NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Unavailable Second"
        ::= { optixTrapsPER  15288 }

--  1.3.6.1.4.1.2011.2.25.3.40.40.30.15289
    perEvtOdu0Tcm1Fesesr NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Ratio of Far End Severely Errored Second"
        ::= { optixTrapsPER  15289 }

--  1.3.6.1.4.1.2011.2.25.3.40.40.30.15290
    perEvtOdu0Tcm1Febber NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Ratio of Far End Background Block Error"
        ::= { optixTrapsPER  15290 }

--  1.3.6.1.4.1.2011.2.25.3.40.40.30.15291
    perEvtOdu0Tcm1Iaes NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section IAE Second"
        ::= { optixTrapsPER  15291 }

--  1.3.6.1.4.1.2011.2.25.3.40.40.30.15292
    perEvtOdu0Tcm1Biaes NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section BIAE Second"
        ::= { optixTrapsPER  15292 }

--  1.3.6.1.4.1.2011.2.25.3.40.40.30.15293
    perEvtOdu0Tcm2Bbe NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Background Block Error"
        ::= { optixTrapsPER  15293 }

--  1.3.6.1.4.1.2011.2.25.3.40.40.30.15294
    perEvtOdu0Tcm2Es NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Errored Second"
        ::= { optixTrapsPER  15294 }

--  1.3.6.1.4.1.2011.2.25.3.40.40.30.15295
    perEvtOdu0Tcm2Ses NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Severely Errored Second"
        ::= { optixTrapsPER  15295 }

--  1.3.6.1.4.1.2011.2.25.3.40.40.30.15296
    perEvtOdu0Tcm2Uas NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Unavailable Second"
        ::= { optixTrapsPER  15296 }

--  1.3.6.1.4.1.2011.2.25.3.40.40.30.15297
    perEvtOdu0Tcm2Sesr NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Ratio of Severely Errored Second"
        ::= { optixTrapsPER  15297 }

--  1.3.6.1.4.1.2011.2.25.3.40.40.30.15298
    perEvtOdu0Tcm2Bber NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Ratio of Background Block Error"
        ::= { optixTrapsPER  15298 }

--  1.3.6.1.4.1.2011.2.25.3.40.40.30.15299
    perEvtOdu0Tcm2Febbe NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Far End Background Block Error"
        ::= { optixTrapsPER  15299 }

--  1.3.6.1.4.1.2011.2.25.3.40.40.30.15300
    perEvtOdu0Tcm2Fees NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Far End Background Block Error"
        ::= { optixTrapsPER  15300 }

--  1.3.6.1.4.1.2011.2.25.3.40.40.30.15301
    perEvtOdu0Tcm2Feses NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Far End Severely Errored Second"
        ::= { optixTrapsPER  15301 }

--  1.3.6.1.4.1.2011.2.25.3.40.40.30.15302
    perEvtOdu0Tcm2Feuas NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Unavailable Second"
        ::= { optixTrapsPER  15302 }

--  1.3.6.1.4.1.2011.2.25.3.40.40.30.15303
    perEvtOdu0Tcm2Fesesr NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Ratio of Far End Severely Errored Second"
        ::= { optixTrapsPER  15303 }

--  1.3.6.1.4.1.2011.2.25.3.40.40.30.15304
    perEvtOdu0Tcm2Febber NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Ratio of Far End Background Block Error"
        ::= { optixTrapsPER  15304 }

--  1.3.6.1.4.1.2011.2.25.3.40.40.30.15305
    perEvtOdu0Tcm2Iaes NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section IAE Second"
        ::= { optixTrapsPER  15305 }

--  1.3.6.1.4.1.2011.2.25.3.40.40.30.15306
    perEvtOdu0Tcm2Biaes NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section BIAE Second"
        ::= { optixTrapsPER  15306 }

--  1.3.6.1.4.1.2011.2.25.3.40.40.30.15307
    perEvtOdu0Tcm3Bbe NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Background Block Error"
        ::= { optixTrapsPER  15307 }

--  1.3.6.1.4.1.2011.2.25.3.40.40.30.15308
    perEvtOdu0Tcm3Es NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Errored Second"
        ::= { optixTrapsPER  15308 }

--  1.3.6.1.4.1.2011.2.25.3.40.40.30.15309
    perEvtOdu0Tcm3Ses NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Severely Errored Second"
        ::= { optixTrapsPER  15309 }

--  1.3.6.1.4.1.2011.2.25.3.40.40.30.15310
    perEvtOdu0Tcm3Uas NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Unavailable Second"
        ::= { optixTrapsPER  15310 }

--  1.3.6.1.4.1.2011.2.25.3.40.40.30.15311
    perEvtOdu0Tcm3Sesr NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Ratio of Severely Errored Second"
        ::= { optixTrapsPER  15311 }

--  1.3.6.1.4.1.2011.2.25.3.40.40.30.15312
    perEvtOdu0Tcm3Bber NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Ratio of Background Block Error"
        ::= { optixTrapsPER  15312 }

--  1.3.6.1.4.1.2011.2.25.3.40.40.30.15313
    perEvtOdu0Tcm3Febbe NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Far End Background Block Error"
        ::= { optixTrapsPER  15313 }

--  1.3.6.1.4.1.2011.2.25.3.40.40.30.15314
    perEvtOdu0Tcm3Fees NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Far End Background Block Error"
        ::= { optixTrapsPER  15314 }

--  1.3.6.1.4.1.2011.2.25.3.40.40.30.15315
    perEvtOdu0Tcm3Feses NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Far End Severely Errored Second"
        ::= { optixTrapsPER  15315 }

--  1.3.6.1.4.1.2011.2.25.3.40.40.30.15316
    perEvtOdu0Tcm3Feuas NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Unavailable Second"
        ::= { optixTrapsPER  15316 }

--  1.3.6.1.4.1.2011.2.25.3.40.40.30.15317
    perEvtOdu0Tcm3Fesesr NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Ratio of Far End Severely Errored Second"
        ::= { optixTrapsPER  15317 }

--  1.3.6.1.4.1.2011.2.25.3.40.40.30.15318
    perEvtOdu0Tcm3Febber NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Ratio of Far End Background Block Error"
        ::= { optixTrapsPER  15318 }

--  1.3.6.1.4.1.2011.2.25.3.40.40.30.15319
    perEvtOdu0Tcm3Iaes NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section IAE Second"
        ::= { optixTrapsPER  15319 }

--  1.3.6.1.4.1.2011.2.25.3.40.40.30.15320
    perEvtOdu0Tcm3Biaes NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section BIAE Second"
        ::= { optixTrapsPER  15320 }

--  1.3.6.1.4.1.2011.2.25.3.40.40.30.15321
    perEvtOdu0Tcm4Bbe NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Background Block Error"
        ::= { optixTrapsPER  15321 }

--  1.3.6.1.4.1.2011.2.25.3.40.40.30.15322
    perEvtOdu0Tcm4Es NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Errored Second"
        ::= { optixTrapsPER  15322 }

--  1.3.6.1.4.1.2011.2.25.3.40.40.30.15323
    perEvtOdu0Tcm4Ses NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Severely Errored Second"
        ::= { optixTrapsPER  15323 }

--  1.3.6.1.4.1.2011.2.25.3.40.40.30.15324
    perEvtOdu0Tcm4Uas NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Unavailable Second"
        ::= { optixTrapsPER  15324 }

--  1.3.6.1.4.1.2011.2.25.3.40.40.30.15325
    perEvtOdu0Tcm4Sesr NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Ratio of Severely Errored Second"
        ::= { optixTrapsPER  15325 }

--  1.3.6.1.4.1.2011.2.25.3.40.40.30.15326
    perEvtOdu0Tcm4Bber NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Ratio of Background Block Error"
        ::= { optixTrapsPER  15326 }

--  1.3.6.1.4.1.2011.2.25.3.40.40.30.15327
    perEvtOdu0Tcm4Febbe NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Far End Background Block Error"
        ::= { optixTrapsPER  15327 }

--  1.3.6.1.4.1.2011.2.25.3.40.40.30.15328
    perEvtOdu0Tcm4Fees NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Far End Background Block Error"
        ::= { optixTrapsPER  15328 }

--  1.3.6.1.4.1.2011.2.25.3.40.40.30.15329
    perEvtOdu0Tcm4Feses NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Far End Severely Errored Second"
        ::= { optixTrapsPER  15329 }

--  1.3.6.1.4.1.2011.2.25.3.40.40.30.15330
    perEvtOdu0Tcm4Feuas NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Unavailable Second"
        ::= { optixTrapsPER  15330 }

--  1.3.6.1.4.1.2011.2.25.3.40.40.30.15331
    perEvtOdu0Tcm4Fesesr NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Ratio of Far End Severely Errored Second"
        ::= { optixTrapsPER  15331 }

--  1.3.6.1.4.1.2011.2.25.3.40.40.30.15332
    perEvtOdu0Tcm4Febber NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Ratio of Far End Background Block Error"
        ::= { optixTrapsPER  15332 }

--  1.3.6.1.4.1.2011.2.25.3.40.40.30.15333
    perEvtOdu0Tcm4Iaes NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section IAE Second"
        ::= { optixTrapsPER  15333 }

--  1.3.6.1.4.1.2011.2.25.3.40.40.30.15334
    perEvtOdu0Tcm4Biaes NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section BIAE Second"
        ::= { optixTrapsPER  15334 }

--  1.3.6.1.4.1.2011.2.25.3.40.40.30.15335
    perEvtOdu0Tcm5Bbe NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Background Block Error"
        ::= { optixTrapsPER  15335 }

--  1.3.6.1.4.1.2011.2.25.3.40.40.30.15336
    perEvtOdu0Tcm5Es NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Errored Second"
        ::= { optixTrapsPER  15336 }

--  1.3.6.1.4.1.2011.2.25.3.40.40.30.15337
    perEvtOdu0Tcm5Ses NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Severely Errored Second"
        ::= { optixTrapsPER  15337 }

--  1.3.6.1.4.1.2011.2.25.3.40.40.30.15338
    perEvtOdu0Tcm5Uas NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Unavailable Second"
        ::= { optixTrapsPER  15338 }

--  1.3.6.1.4.1.2011.2.25.3.40.40.30.15339
    perEvtOdu0Tcm5Sesr NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Ratio of Severely Errored Second"
        ::= { optixTrapsPER  15339 }

--  1.3.6.1.4.1.2011.2.25.3.40.40.30.15340
    perEvtOdu0Tcm5Bber NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Ratio of Background Block Error"
        ::= { optixTrapsPER  15340 }

--  1.3.6.1.4.1.2011.2.25.3.40.40.30.15341
    perEvtOdu0Tcm5Febbe NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Far End Background Block Error"
        ::= { optixTrapsPER  15341 }

--  1.3.6.1.4.1.2011.2.25.3.40.40.30.15342
    perEvtOdu0Tcm5Fees NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Far End Background Block Error"
        ::= { optixTrapsPER  15342 }

--  1.3.6.1.4.1.2011.2.25.3.40.40.30.15343
    perEvtOdu0Tcm5Feses NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Far End Severely Errored Second"
        ::= { optixTrapsPER  15343 }

--  1.3.6.1.4.1.2011.2.25.3.40.40.30.15344
    perEvtOdu0Tcm5Feuas NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Unavailable Second"
        ::= { optixTrapsPER  15344 }

--  1.3.6.1.4.1.2011.2.25.3.40.40.30.15345
    perEvtOdu0Tcm5Fesesr NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Ratio of Far End Severely Errored Second"
        ::= { optixTrapsPER  15345 }

--  1.3.6.1.4.1.2011.2.25.3.40.40.30.15346
    perEvtOdu0Tcm5Febber NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Ratio of Far End Background Block Error"
        ::= { optixTrapsPER  15346 }

--  1.3.6.1.4.1.2011.2.25.3.40.40.30.15347
    perEvtOdu0Tcm5Iaes NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section IAE Second"
        ::= { optixTrapsPER  15347 }

--  1.3.6.1.4.1.2011.2.25.3.40.40.30.15348
    perEvtOdu0Tcm5Biaes NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section BIAE Second"
        ::= { optixTrapsPER  15348 }

--  1.3.6.1.4.1.2011.2.25.3.40.40.30.15349
    perEvtOdu0Tcm6Bbe NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Background Block Error"
        ::= { optixTrapsPER  15349 }

--  1.3.6.1.4.1.2011.2.25.3.40.40.30.15350
    perEvtOdu0Tcm6Es NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Errored Second"
        ::= { optixTrapsPER  15350 }

--  1.3.6.1.4.1.2011.2.25.3.40.40.30.15351
    perEvtOdu0Tcm6Ses NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Severely Errored Second"
        ::= { optixTrapsPER  15351 }

--  1.3.6.1.4.1.2011.2.25.3.40.40.30.15352
    perEvtOdu0Tcm6Uas NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Unavailable Second"
        ::= { optixTrapsPER  15352 }

--  1.3.6.1.4.1.2011.2.25.3.40.40.30.15353
    perEvtOdu0Tcm6Sesr NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Ratio of Severely Errored Second"
        ::= { optixTrapsPER  15353 }

--  1.3.6.1.4.1.2011.2.25.3.40.40.30.15354
    perEvtOdu0Tcm6Bber NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Ratio of Background Block Error"
        ::= { optixTrapsPER  15354 }

--  1.3.6.1.4.1.2011.2.25.3.40.40.30.15355
    perEvtOdu0Tcm6Febbe NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Far End Background Block Error"
        ::= { optixTrapsPER  15355 }

--  1.3.6.1.4.1.2011.2.25.3.40.40.30.15356
    perEvtOdu0Tcm6Fees NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Far End Background Block Error"
        ::= { optixTrapsPER  15356 }

--  1.3.6.1.4.1.2011.2.25.3.40.40.30.15357
    perEvtOdu0Tcm6Feses NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Far End Severely Errored Second"
        ::= { optixTrapsPER  15357 }

--  1.3.6.1.4.1.2011.2.25.3.40.40.30.15358
    perEvtOdu0Tcm6Feuas NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Unavailable Second"
        ::= { optixTrapsPER  15358 }

--  1.3.6.1.4.1.2011.2.25.3.40.40.30.15359
    perEvtOdu0Tcm6Fesesr NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Ratio of Far End Severely Errored Second"
        ::= { optixTrapsPER  15359 }

--  1.3.6.1.4.1.2011.2.25.3.40.40.30.15360
    perEvtOdu0Tcm6Febber NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section Ratio of Far End Background Block Error"
        ::= { optixTrapsPER  15360 }

--  1.3.6.1.4.1.2011.2.25.3.40.40.30.15361
    perEvtOdu0Tcm6Iaes NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section IAE Second"
        ::= { optixTrapsPER  15361 }

--  1.3.6.1.4.1.2011.2.25.3.40.40.30.15362
    perEvtOdu0Tcm6Biaes NOTIFICATION-TYPE
        OBJECTS { rptEvtPeriod, rptEvtValue, rptEvtVldty, rptEvtDateTime, rptEvtObjType, rptEvtParaLen, rptEvtPara}
        STATUS current
        DESCRIPTION
        "Trap of PerEvt: ODU0 TCMn Section BIAE Second"
        ::= { optixTrapsPER  15362 }

--  1.3.6.1.4.1.2011.2.25.3.40.40.30.15423
    perEvtOdu0PmTmp NOTIFICATION-TYPE
        OBJECTS { rptEvtPeriod, rptEvtValue, rptEvtVldty, rptEvtDateTime, rptEvtObjType, rptEvtParaLen, rptEvtPara}
        STATUS current
        DESCRIPTION
        "Trap of PerEvt: ODU0 PM Section Total Monitor Period"
        ::= { optixTrapsPER  15423 }

--  1.3.6.1.4.1.2011.2.25.3.40.40.30.15424
    perEvtOdu0Tcm1Tmp NOTIFICATION-TYPE
        OBJECTS { rptEvtPeriod, rptEvtValue, rptEvtVldty, rptEvtDateTime, rptEvtObjType, rptEvtParaLen, rptEvtPara}
        STATUS current
        DESCRIPTION
        "Trap of PerEvt: ODU0 TCM1 Section Total Monitor Period"
        ::= { optixTrapsPER  15424 }

--  1.3.6.1.4.1.2011.2.25.3.40.40.30.15425
    perEvtOdu0Tcm2Tmp NOTIFICATION-TYPE
        OBJECTS { rptEvtPeriod, rptEvtValue, rptEvtVldty, rptEvtDateTime, rptEvtObjType, rptEvtParaLen, rptEvtPara}
        STATUS current
        DESCRIPTION
        "Trap of PerEvt: ODU0 TCM2 Section Total Monitor Period"
        ::= { optixTrapsPER  15425 }

--  1.3.6.1.4.1.2011.2.25.3.40.40.30.15426
    perEvtOdu0Tcm3Tmp NOTIFICATION-TYPE
        OBJECTS { rptEvtPeriod, rptEvtValue, rptEvtVldty, rptEvtDateTime, rptEvtObjType, rptEvtParaLen, rptEvtPara}
        STATUS current
        DESCRIPTION
        "Trap of PerEvt: ODU0 TCM3 Section Total Monitor Period"
        ::= { optixTrapsPER  15426 }

--  1.3.6.1.4.1.2011.2.25.3.40.40.30.15427
    perEvtOdu0Tcm4Tmp NOTIFICATION-TYPE
        OBJECTS { rptEvtPeriod, rptEvtValue, rptEvtVldty, rptEvtDateTime, rptEvtObjType, rptEvtParaLen, rptEvtPara}
        STATUS current
        DESCRIPTION
        "Trap of PerEvt: ODU0 TCM4 Section Total Monitor Period"
        ::= { optixTrapsPER  15427 }

--  1.3.6.1.4.1.2011.2.25.3.40.40.30.15428
    perEvtOdu0Tcm5Tmp NOTIFICATION-TYPE
        OBJECTS { rptEvtPeriod, rptEvtValue, rptEvtVldty, rptEvtDateTime, rptEvtObjType, rptEvtParaLen, rptEvtPara}
        STATUS current
        DESCRIPTION
        "Trap of PerEvt: ODU0 TCM5 Section Total Monitor Period"
        ::= { optixTrapsPER  15428 }

--  1.3.6.1.4.1.2011.2.25.3.40.40.30.15429
    perEvtOdu0Tcm6Tmp NOTIFICATION-TYPE
        OBJECTS { rptEvtPeriod, rptEvtValue, rptEvtVldty, rptEvtDateTime, rptEvtObjType, rptEvtParaLen, rptEvtPara}
        STATUS current
        DESCRIPTION
        "Trap of PerEvt: ODU0 TCM6 Section Total Monitor Period"
        ::= { optixTrapsPER  15429 }

--  1.3.6.1.4.1.2011.2.25.3.40.40.30.15430
    perEvtOtu1Tmp NOTIFICATION-TYPE
        OBJECTS { rptEvtPeriod, rptEvtValue, rptEvtVldty, rptEvtDateTime, rptEvtObjType, rptEvtParaLen, rptEvtPara}
        STATUS current
        DESCRIPTION
        "Trap of PerEvt: OTU1 SM Section Total Monitor Period"
        ::= { optixTrapsPER  15430 }

--  1.3.6.1.4.1.2011.2.25.3.40.40.30.15431
    perEvtOdu1PmTmp NOTIFICATION-TYPE
        OBJECTS { rptEvtPeriod, rptEvtValue, rptEvtVldty, rptEvtDateTime, rptEvtObjType, rptEvtParaLen, rptEvtPara}
        STATUS current
        DESCRIPTION
        "Trap of PerEvt: ODU1 PM Section Total Monitor Period"
        ::= { optixTrapsPER  15431 }

--  1.3.6.1.4.1.2011.2.25.3.40.40.30.15432
    perEvtOdu1Tcm1Tmp NOTIFICATION-TYPE
        OBJECTS { rptEvtPeriod, rptEvtValue, rptEvtVldty, rptEvtDateTime, rptEvtObjType, rptEvtParaLen, rptEvtPara}
        STATUS current
        DESCRIPTION
        "Trap of PerEvt: ODU1 TCM1 Section Total Monitor Period"
        ::= { optixTrapsPER  15432 }

--  1.3.6.1.4.1.2011.2.25.3.40.40.30.15433
    perEvtOdu1Tcm2Tmp NOTIFICATION-TYPE
        OBJECTS { rptEvtPeriod, rptEvtValue, rptEvtVldty, rptEvtDateTime, rptEvtObjType, rptEvtParaLen, rptEvtPara}
        STATUS current
        DESCRIPTION
        "Trap of PerEvt: ODU1 TCM2 Section Total Monitor Period"
        ::= { optixTrapsPER  15433 }

--  1.3.6.1.4.1.2011.2.25.3.40.40.30.15434
    perEvtOdu1Tcm3Tmp NOTIFICATION-TYPE
        OBJECTS { rptEvtPeriod, rptEvtValue, rptEvtVldty, rptEvtDateTime, rptEvtObjType, rptEvtParaLen, rptEvtPara}
        STATUS current
        DESCRIPTION
        "Trap of PerEvt: ODU1 TCM3 Section Total Monitor Period"
        ::= { optixTrapsPER  15434 }

--  1.3.6.1.4.1.2011.2.25.3.40.40.30.15435
    perEvtOdu1Tcm4Tmp NOTIFICATION-TYPE
        OBJECTS { rptEvtPeriod, rptEvtValue, rptEvtVldty, rptEvtDateTime, rptEvtObjType, rptEvtParaLen, rptEvtPara}
        STATUS current
        DESCRIPTION
        "Trap of PerEvt: ODU1 TCM4 Section Total Monitor Period"
        ::= { optixTrapsPER  15435 }

--  1.3.6.1.4.1.2011.2.25.3.40.40.30.15436
    perEvtOdu1Tcm5Tmp NOTIFICATION-TYPE
        OBJECTS { rptEvtPeriod, rptEvtValue, rptEvtVldty, rptEvtDateTime, rptEvtObjType, rptEvtParaLen, rptEvtPara}
        STATUS current
        DESCRIPTION
        "Trap of PerEvt: ODU1 TCM5 Section Total Monitor Period"
        ::= { optixTrapsPER  15436 }

--  1.3.6.1.4.1.2011.2.25.3.40.40.30.15437
    perEvtOdu1Tcm6Tmp NOTIFICATION-TYPE
        OBJECTS { rptEvtPeriod, rptEvtValue, rptEvtVldty, rptEvtDateTime, rptEvtObjType, rptEvtParaLen, rptEvtPara}
        STATUS current
        DESCRIPTION
        "Trap of PerEvt: ODU1 TCM6 Section Total Monitor Period"
        ::= { optixTrapsPER  15437 }

--  1.3.6.1.4.1.2011.2.25.3.40.40.30.15438
    perEvtOtu2Tmp NOTIFICATION-TYPE
        OBJECTS { rptEvtPeriod, rptEvtValue, rptEvtVldty, rptEvtDateTime, rptEvtObjType, rptEvtParaLen, rptEvtPara}
        STATUS current
        DESCRIPTION
        "Trap of PerEvt: OTU2 SM Section Total Monitor Period"
        ::= { optixTrapsPER  15438 }

--  1.3.6.1.4.1.2011.2.25.3.40.40.30.15440
    perEvtOdu2Tcm1Tmp NOTIFICATION-TYPE
        OBJECTS { rptEvtPeriod, rptEvtValue, rptEvtVldty, rptEvtDateTime, rptEvtObjType, rptEvtParaLen, rptEvtPara}
        STATUS current
        DESCRIPTION
        "Trap of PerEvt: ODU2 TCM1 Section Total Monitor Period"
        ::= { optixTrapsPER  15440 }

--  1.3.6.1.4.1.2011.2.25.3.40.40.30.15441
    perEvtOdu2Tcm2Tmp NOTIFICATION-TYPE
        OBJECTS { rptEvtPeriod, rptEvtValue, rptEvtVldty, rptEvtDateTime, rptEvtObjType, rptEvtParaLen, rptEvtPara}
        STATUS current
        DESCRIPTION
        "Trap of PerEvt: ODU2 TCM2 Section Total Monitor Period"
        ::= { optixTrapsPER  15441 }

--  1.3.6.1.4.1.2011.2.25.3.40.40.30.15442
    perEvtOdu2Tcm3Tmp NOTIFICATION-TYPE
        OBJECTS { rptEvtPeriod, rptEvtValue, rptEvtVldty, rptEvtDateTime, rptEvtObjType, rptEvtParaLen, rptEvtPara}
        STATUS current
        DESCRIPTION
        "Trap of PerEvt: ODU2 TCM3 Section Total Monitor Period"
        ::= { optixTrapsPER  15442 }

--  1.3.6.1.4.1.2011.2.25.3.40.40.30.15443
    perEvtOdu2Tcm4Tmp NOTIFICATION-TYPE
        OBJECTS { rptEvtPeriod, rptEvtValue, rptEvtVldty, rptEvtDateTime, rptEvtObjType, rptEvtParaLen, rptEvtPara}
        STATUS current
        DESCRIPTION
        "Trap of PerEvt: ODU2 TCM4 Section Total Monitor Period"
        ::= { optixTrapsPER  15443 }

--  1.3.6.1.4.1.2011.2.25.3.40.40.30.15444
    perEvtOdu2Tcm5Tmp NOTIFICATION-TYPE
        OBJECTS { rptEvtPeriod, rptEvtValue, rptEvtVldty, rptEvtDateTime, rptEvtObjType, rptEvtParaLen, rptEvtPara}
        STATUS current
        DESCRIPTION
        "Trap of PerEvt: ODU2 TCM5 Section Total Monitor Period"
        ::= { optixTrapsPER  15444 }

--  1.3.6.1.4.1.2011.2.25.3.40.40.30.15445
    perEvtOdu2Tcm6Tmp NOTIFICATION-TYPE
        OBJECTS { rptEvtPeriod, rptEvtValue, rptEvtVldty, rptEvtDateTime, rptEvtObjType, rptEvtParaLen, rptEvtPara}
        STATUS current
        DESCRIPTION
        "Trap of PerEvt: ODU2 TCM6 Section Total Monitor Period"
        ::= { optixTrapsPER  15445 }

--  1.3.6.1.4.1.2011.2.25.3.40.40.30.15446
    perEvtOtu3Tmp  NOTIFICATION-TYPE
        OBJECTS { rptEvtPeriod, rptEvtValue, rptEvtVldty, rptEvtDateTime, rptEvtObjType, rptEvtParaLen, rptEvtPara}
        STATUS current
        DESCRIPTION
        "Trap of PerEvt: OTU3 SM Section Total Monitor Period"
        ::= { optixTrapsPER  15446 }

--  1.3.6.1.4.1.2011.2.25.3.40.40.30.15448
    perEvtOdu3Tcm1Tmp NOTIFICATION-TYPE
        OBJECTS { rptEvtPeriod, rptEvtValue, rptEvtVldty, rptEvtDateTime, rptEvtObjType, rptEvtParaLen, rptEvtPara}
        STATUS current
        DESCRIPTION
        "Trap of PerEvt: ODU3 TCM1 Section Total Monitor Period"
        ::= { optixTrapsPER  15448 }

--  1.3.6.1.4.1.2011.2.25.3.40.40.30.15449
    perEvtOdu3Tcm2Tmp NOTIFICATION-TYPE
        OBJECTS { rptEvtPeriod, rptEvtValue, rptEvtVldty, rptEvtDateTime, rptEvtObjType, rptEvtParaLen, rptEvtPara}
        STATUS current
        DESCRIPTION
        "Trap of PerEvt: ODU3 TCM2 Section Total Monitor Period"
        ::= { optixTrapsPER  15449 }

--  1.3.6.1.4.1.2011.2.25.3.40.40.30.15450
    perEvtOdu3Tcm3Tmp NOTIFICATION-TYPE
        OBJECTS { rptEvtPeriod, rptEvtValue, rptEvtVldty, rptEvtDateTime, rptEvtObjType, rptEvtParaLen, rptEvtPara}
        STATUS current
        DESCRIPTION
        "Trap of PerEvt: ODU3 TCM3 Section Total Monitor Period"
        ::= { optixTrapsPER  15450 }

--  1.3.6.1.4.1.2011.2.25.3.40.40.30.15451
    perEvtOdu3Tcm4Tmp NOTIFICATION-TYPE
        OBJECTS { rptEvtPeriod, rptEvtValue, rptEvtVldty, rptEvtDateTime, rptEvtObjType, rptEvtParaLen, rptEvtPara}
        STATUS current
        DESCRIPTION
        "Trap of PerEvt: ODU3 TCM4 Section Total Monitor Period"
        ::= { optixTrapsPER  15451 }

--  1.3.6.1.4.1.2011.2.25.3.40.40.30.15452
    perEvtOdu3Tcm5Tmp NOTIFICATION-TYPE
        OBJECTS { rptEvtPeriod, rptEvtValue, rptEvtVldty, rptEvtDateTime, rptEvtObjType, rptEvtParaLen, rptEvtPara}
        STATUS current
        DESCRIPTION
        "Trap of PerEvt: ODU3 TCM5 Section Total Monitor Period"
        ::= { optixTrapsPER  15452 }

--  1.3.6.1.4.1.2011.2.25.3.40.40.30.15453
    perEvtOdu3Tcm6Tmp NOTIFICATION-TYPE
        OBJECTS { rptEvtPeriod, rptEvtValue, rptEvtVldty, rptEvtDateTime, rptEvtObjType, rptEvtParaLen, rptEvtPara}
        STATUS current
        DESCRIPTION
        "Trap of PerEvt: ODU3 TCM6 Section Total Monitor Period"
        ::= { optixTrapsPER  15453 }

--  1.3.6.1.4.1.2011.2.25.3.40.40.30.15456
    perEvtOdu4Tcm1Tmp NOTIFICATION-TYPE
        OBJECTS { rptEvtPeriod, rptEvtValue, rptEvtVldty, rptEvtDateTime, rptEvtObjType, rptEvtParaLen, rptEvtPara}
        STATUS current
        DESCRIPTION
        "Trap of PerEvt: ODU4 TCM1 Section Total Monitor Period"
        ::= { optixTrapsPER  15456 }

--  1.3.6.1.4.1.2011.2.25.3.40.40.30.15457
    perEvtOdu4Tcm2Tmp NOTIFICATION-TYPE
        OBJECTS { rptEvtPeriod, rptEvtValue, rptEvtVldty, rptEvtDateTime, rptEvtObjType, rptEvtParaLen, rptEvtPara}
        STATUS current
        DESCRIPTION
        "Trap of PerEvt: ODU4 TCM2 Section Total Monitor Period"
        ::= { optixTrapsPER  15457 }

--  1.3.6.1.4.1.2011.2.25.3.40.40.30.15458
    perEvtOdu4Tcm3Tmp NOTIFICATION-TYPE
        OBJECTS { rptEvtPeriod, rptEvtValue, rptEvtVldty, rptEvtDateTime, rptEvtObjType, rptEvtParaLen, rptEvtPara}
        STATUS current
        DESCRIPTION
        "Trap of PerEvt: ODU4 TCM3 Section Total Monitor Period"
        ::= { optixTrapsPER  15458 }

--  1.3.6.1.4.1.2011.2.25.3.40.40.30.15459
    perEvtOdu4Tcm4Tmp NOTIFICATION-TYPE
        OBJECTS { rptEvtPeriod, rptEvtValue, rptEvtVldty, rptEvtDateTime, rptEvtObjType, rptEvtParaLen, rptEvtPara}
        STATUS current
        DESCRIPTION
        "Trap of PerEvt: ODU4 TCM4 Section Total Monitor Period"
        ::= { optixTrapsPER  15459 }

--  1.3.6.1.4.1.2011.2.25.3.40.40.30.15460
    perEvtOdu4Tcm5Tmp NOTIFICATION-TYPE
        OBJECTS { rptEvtPeriod, rptEvtValue, rptEvtVldty, rptEvtDateTime, rptEvtObjType, rptEvtParaLen, rptEvtPara}
        STATUS current
        DESCRIPTION
        "Trap of PerEvt: ODU4 TCM5 Section Total Monitor Period"
        ::= { optixTrapsPER  15460 }

--  1.3.6.1.4.1.2011.2.25.3.40.40.30.15461
    perEvtOdu4Tcm6Tmp NOTIFICATION-TYPE
        OBJECTS { rptEvtPeriod, rptEvtValue, rptEvtVldty, rptEvtDateTime, rptEvtObjType, rptEvtParaLen, rptEvtPara}
        STATUS current
        DESCRIPTION
        "Trap of PerEvt: ODU4 TCM6 Section Total Monitor Period"
        ::= { optixTrapsPER  15461 }

--  1.3.6.1.4.1.2011.2.25.3.40.40.30.15471
    perEvtFecTmp NOTIFICATION-TYPE
        OBJECTS { rptEvtPeriod, rptEvtValue, rptEvtVldty, rptEvtDateTime, rptEvtObjType, rptEvtParaLen, rptEvtPara}
        STATUS current
        DESCRIPTION
        "Trap of PerEvt: FEC Total Monitor Period"
        ::= { optixTrapsPER  15471 }

--  1.3.6.1.4.1.2011.2.25.3.40.40.30.15472
    perEvtRsTmp NOTIFICATION-TYPE
        OBJECTS { rptEvtPeriod, rptEvtValue, rptEvtVldty, rptEvtDateTime, rptEvtObjType, rptEvtParaLen, rptEvtPara}
        STATUS current
        DESCRIPTION
        "Trap of PerEvt: RS Total Monitoring Period"
        ::= { optixTrapsPER  15472 }

--  1.3.6.1.4.1.2011.2.25.3.40.40.30.15511
    perEvtOduflexTcm6Fesesr NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Ratio of Far End Severely Errored Second"
        ::= { optixTrapsPER  15511 }

--  1.3.6.1.4.1.2011.2.25.3.40.40.30.15512
    perEvtOduflexTcm5Tmp NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCM5 Section Total Monitor Period"
        ::= { optixTrapsPER  15512 }

--  1.3.6.1.4.1.2011.2.25.3.40.40.30.15513
    perEvtOduflexTcm6Feuas NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Unavailable Second"
        ::= { optixTrapsPER  15513 }

--  1.3.6.1.4.1.2011.2.25.3.40.40.30.15514
    perEvtOduflexTcm6Feses NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Far End Severely Errored Second"
        ::= { optixTrapsPER  15514 }

--  1.3.6.1.4.1.2011.2.25.3.40.40.30.15515
    perEvtOduflexTcm6Ses NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Severely Errored Second"
        ::= { optixTrapsPER  15515 }

--  1.3.6.1.4.1.2011.2.25.3.40.40.30.15516
    perEvtOduflexTcm6Fees NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Far End Background Block Error"
        ::= { optixTrapsPER  15516 }

--  1.3.6.1.4.1.2011.2.25.3.40.40.30.15517
    perEvtOduflexTcm6Es NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Errored Second"
        ::= { optixTrapsPER  15517 }

--  1.3.6.1.4.1.2011.2.25.3.40.40.30.15518
    perEvtOduflexTcm6Bbe NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Background Block Error"
        ::= { optixTrapsPER  15518 }

--  1.3.6.1.4.1.2011.2.25.3.40.40.30.15519
    perEvtOduflexTcm6Bber NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Ratio of Background Block Error"
        ::= { optixTrapsPER  15519 }

--  1.3.6.1.4.1.2011.2.25.3.40.40.30.15520
    perEvtOduflexTcm6Febbe NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Far End Background Block Error"
        ::= { optixTrapsPER  15520 }

--  1.3.6.1.4.1.2011.2.25.3.40.40.30.15521
    perEvtOduflexTcm6Sesr NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Ratio of Severely Errored Second"
        ::= { optixTrapsPER  15521 }

--  1.3.6.1.4.1.2011.2.25.3.40.40.30.15522
    perEvtOduflexTcm6Uas NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Unavailable Second"
        ::= { optixTrapsPER  15522 }

--  1.3.6.1.4.1.2011.2.25.3.40.40.30.15523
    perEvtOduflexTcm6Iaes NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section IAE Second"
        ::= { optixTrapsPER  15523 }

--  1.3.6.1.4.1.2011.2.25.3.40.40.30.15524
    perEvtOduflexTcm6Biaes NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section BIAE Second"
        ::= { optixTrapsPER  15524 }

--  1.3.6.1.4.1.2011.2.25.3.40.40.30.15525
    perEvtOduflexTcm6Febber NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Ratio of Far End Background Block Error"
        ::= { optixTrapsPER  15525 }

--  1.3.6.1.4.1.2011.2.25.3.40.40.30.15526
    perEvtOduflexTcm6Tmp NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCM6 Section Total Monitor Period"
        ::= { optixTrapsPER  15526 }

--  1.3.6.1.4.1.2011.2.25.3.40.40.30.15527
    perEvtOduflexTcm2Uas NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Unavailable Second"
        ::= { optixTrapsPER  15527 }

--  1.3.6.1.4.1.2011.2.25.3.40.40.30.15528
    perEvtOduflexTcm1Febbe NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Far End Background Block Error"
        ::= { optixTrapsPER  15528 }

--  1.3.6.1.4.1.2011.2.25.3.40.40.30.15529
    perEvtOduflexTcm5Febber NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Ratio of Far End Background Block Error"
        ::= { optixTrapsPER  15529 }

--  1.3.6.1.4.1.2011.2.25.3.40.40.30.15530
    perEvtOduflexTcm5Fesesr NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Ratio of Far End Severely Errored Second"
        ::= { optixTrapsPER  15530 }

--  1.3.6.1.4.1.2011.2.25.3.40.40.30.15531
    perEvtOduflexTcm5Bber NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Ratio of Background Block Error"
        ::= { optixTrapsPER  15531 }

--  1.3.6.1.4.1.2011.2.25.3.40.40.30.15532
    perEvtOduflexTcm5Sesr NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Ratio of Severely Errored Second"
        ::= { optixTrapsPER  15532 }

--  1.3.6.1.4.1.2011.2.25.3.40.40.30.15533
    perEvtOduflexTcm5Fees NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Far End Background Block Error"
        ::= { optixTrapsPER  15533 }

--  1.3.6.1.4.1.2011.2.25.3.40.40.30.15534
    perEvtOduflexTcm5Febbe NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Far End Background Block Error"
        ::= { optixTrapsPER  15534 }

--  1.3.6.1.4.1.2011.2.25.3.40.40.30.15535
    perEvtOduflexTcm5Feuas NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Unavailable Second"
        ::= { optixTrapsPER  15535 }

--  1.3.6.1.4.1.2011.2.25.3.40.40.30.15536
    perEvtOduflexTcm5Feses NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Far End Severely Errored Second"
        ::= { optixTrapsPER  15536 }

--  1.3.6.1.4.1.2011.2.25.3.40.40.30.15537
    perEvtOduflexTcm5Uas NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Unavailable Second"
        ::= { optixTrapsPER  15537 }

--  1.3.6.1.4.1.2011.2.25.3.40.40.30.15538
    perEvtOduflexTcm5Ses NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Severely Errored Second"
        ::= { optixTrapsPER  15538 }

--  1.3.6.1.4.1.2011.2.25.3.40.40.30.15539
    perEvtOduflexTcm5Es NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Errored Second"
        ::= { optixTrapsPER  15539 }

--  1.3.6.1.4.1.2011.2.25.3.40.40.30.15540
    perEvtOduflexTcm5Bbe NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Background Block Error"
        ::= { optixTrapsPER  15540 }

--  1.3.6.1.4.1.2011.2.25.3.40.40.30.15541
    perEvtOduflexTcm5Biaes NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section BIAE Second"
        ::= { optixTrapsPER  15541 }

--  1.3.6.1.4.1.2011.2.25.3.40.40.30.15542
    perEvtOduflexTcm5Iaes NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section IAE Second"
        ::= { optixTrapsPER  15542 }

--  1.3.6.1.4.1.2011.2.25.3.40.40.30.15543
    perEvtOduflexTcm4Biaes NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section BIAE Second"
        ::= { optixTrapsPER  15543 }

--  1.3.6.1.4.1.2011.2.25.3.40.40.30.15544
    perEvtOduflexTcm4Iaes NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section IAE Second"
        ::= { optixTrapsPER  15544 }

--  1.3.6.1.4.1.2011.2.25.3.40.40.30.15545
    perEvtOduflexTcm4Febber NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Ratio of Far End Background Block Error"
        ::= { optixTrapsPER  15545 }

--  1.3.6.1.4.1.2011.2.25.3.40.40.30.15546
    perEvtOduflexTcm4Fesesr NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Ratio of Far End Severely Errored Second"
        ::= { optixTrapsPER  15546 }

--  1.3.6.1.4.1.2011.2.25.3.40.40.30.15547
    perEvtOduflexTcm4Feuas NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Unavailable Second"
        ::= { optixTrapsPER  15547 }

--  1.3.6.1.4.1.2011.2.25.3.40.40.30.15548
    perEvtOduflexTcm4Feses NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Far End Severely Errored Second"
        ::= { optixTrapsPER  15548 }

--  1.3.6.1.4.1.2011.2.25.3.40.40.30.15549
    perEvtOduflexTcm4Fees NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Far End Background Block Error"
        ::= { optixTrapsPER  15549 }

--  1.3.6.1.4.1.2011.2.25.3.40.40.30.15550
    perEvtOduflexTcm4Febbe NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Far End Background Block Error"
        ::= { optixTrapsPER  15550 }

--  1.3.6.1.4.1.2011.2.25.3.40.40.30.15551
    perEvtOduflexTcm4Uas NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Unavailable Second"
        ::= { optixTrapsPER  15551 }

--  1.3.6.1.4.1.2011.2.25.3.40.40.30.15552
    perEvtOduflexTcm4Ses NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Severely Errored Second"
        ::= { optixTrapsPER  15552 }

--  1.3.6.1.4.1.2011.2.25.3.40.40.30.15553
    perEvtOduflexTcm4Bber NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Ratio of Background Block Error"
        ::= { optixTrapsPER  15553 }

--  1.3.6.1.4.1.2011.2.25.3.40.40.30.15554
    perEvtOduflexTcm4Sesr NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Ratio of Severely Errored Second"
        ::= { optixTrapsPER  15554 }

--  1.3.6.1.4.1.2011.2.25.3.40.40.30.15555
    perEvtOduflexTcm4Es NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Errored Second"
        ::= { optixTrapsPER  15555 }

--  1.3.6.1.4.1.2011.2.25.3.40.40.30.15556
    perEvtOduflexTcm4Bbe NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Background Block Error"
        ::= { optixTrapsPER  15556 }

--  1.3.6.1.4.1.2011.2.25.3.40.40.30.15557
    perEvtOduflexTcm4Tmp NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCM4 Section Total Monitor Period"
        ::= { optixTrapsPER  15557 }

--  1.3.6.1.4.1.2011.2.25.3.40.40.30.15558
    perEvtOduflexTcm1Fesesr NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Ratio of Far End Severely Errored Second"
        ::= { optixTrapsPER  15558 }

--  1.3.6.1.4.1.2011.2.25.3.40.40.30.15559
    perEvtOduflexTcm1Biaes NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section BIAE Second"
        ::= { optixTrapsPER  15559 }

--  1.3.6.1.4.1.2011.2.25.3.40.40.30.15560
    perEvtOduflexTcm1Febber NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Ratio of Far End Background Block Error"
        ::= { optixTrapsPER  15560 }

--  1.3.6.1.4.1.2011.2.25.3.40.40.30.15561
    perEvtOduflexTcm1Iaes NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section IAE Second"
        ::= { optixTrapsPER  15561 }

--  1.3.6.1.4.1.2011.2.25.3.40.40.30.15562
    perEvtOduflexTcm1Feuas NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Unavailable Second"
        ::= { optixTrapsPER  15562 }

--  1.3.6.1.4.1.2011.2.25.3.40.40.30.15563
    perEvtOduflexTcm1Feses NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Far End Severely Errored Second"
        ::= { optixTrapsPER  15563 }

--  1.3.6.1.4.1.2011.2.25.3.40.40.30.15564
    perEvtOduflexTcm1Sesr NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Ratio of Severely Errored Second"
        ::= { optixTrapsPER  15564 }

--  1.3.6.1.4.1.2011.2.25.3.40.40.30.15565
    perEvtOduflexTcm1Bber NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Ratio of Background Block Error"
        ::= { optixTrapsPER  15565 }

--  1.3.6.1.4.1.2011.2.25.3.40.40.30.15566
    perEvtOduflexTcm1Fees NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Far End Background Block Error"
        ::= { optixTrapsPER  15566 }

--  1.3.6.1.4.1.2011.2.25.3.40.40.30.15567
    perEvtOduflexTcm1Bbe NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Background Block Error"
        ::= { optixTrapsPER  15567 }

--  1.3.6.1.4.1.2011.2.25.3.40.40.30.15568
    perEvtOduflexTcm1Es NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Errored Second"
        ::= { optixTrapsPER  15568 }

--  1.3.6.1.4.1.2011.2.25.3.40.40.30.15569
    perEvtOduflexTcm1Ses NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Severely Errored Second"
        ::= { optixTrapsPER  15569 }

--  1.3.6.1.4.1.2011.2.25.3.40.40.30.15570
    perEvtOduflexTcm1Uas NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Unavailable Second"
        ::= { optixTrapsPER  15570 }

--  1.3.6.1.4.1.2011.2.25.3.40.40.30.15571
    perEvtOduflexTcm1Tmp NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCM1 Section Total Monitor Period"
        ::= { optixTrapsPER  15571 }

--  1.3.6.1.4.1.2011.2.25.3.40.40.30.15572
    perEvtOduflexTcm2Febbe NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Far End Background Block Error"
        ::= { optixTrapsPER  15572 }

--  1.3.6.1.4.1.2011.2.25.3.40.40.30.15573
    perEvtOduflexTcm2Fees NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Far End Background Block Error"
        ::= { optixTrapsPER  15573 }

--  1.3.6.1.4.1.2011.2.25.3.40.40.30.15574
    perEvtOduflexTcm2Feses NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Far End Severely Errored Second"
        ::= { optixTrapsPER  15574 }

--  1.3.6.1.4.1.2011.2.25.3.40.40.30.15575
    perEvtOduflexTcm2Feuas NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Unavailable Second"
        ::= { optixTrapsPER  15575 }

--  1.3.6.1.4.1.2011.2.25.3.40.40.30.15576
    perEvtOduflexTcm2Fesesr NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Ratio of Far End Severely Errored Second"
        ::= { optixTrapsPER  15576 }

--  1.3.6.1.4.1.2011.2.25.3.40.40.30.15577
    perEvtOduflexTcm2Febber NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Ratio of Far End Background Block Error"
        ::= { optixTrapsPER  15577 }

--  1.3.6.1.4.1.2011.2.25.3.40.40.30.15578
    perEvtOduflexTcm2Iaes NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section IAE Second"
        ::= { optixTrapsPER  15578 }

--  1.3.6.1.4.1.2011.2.25.3.40.40.30.15579
    perEvtOduflexTcm2Biaes NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section BIAE Second"
        ::= { optixTrapsPER  15579 }

--  1.3.6.1.4.1.2011.2.25.3.40.40.30.15580
    perEvtOduflexTcm2Bber NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Ratio of Background Block Error"
        ::= { optixTrapsPER  15580 }

--  1.3.6.1.4.1.2011.2.25.3.40.40.30.15581
    perEvtOduflexTcm2Sesr NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Ratio of Severely Errored Second"
        ::= { optixTrapsPER  15581 }

--  1.3.6.1.4.1.2011.2.25.3.40.40.30.15582
    perEvtOduflexTcm2Es NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Errored Second"
        ::= { optixTrapsPER  15582 }

--  1.3.6.1.4.1.2011.2.25.3.40.40.30.15583
    perEvtOduflexTcm2Ses NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Severely Errored Second"
        ::= { optixTrapsPER  15583 }

--  1.3.6.1.4.1.2011.2.25.3.40.40.30.15584
    perEvtOduflexTcm2Bbe NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Background Block Error"
        ::= { optixTrapsPER  15584 }

--  1.3.6.1.4.1.2011.2.25.3.40.40.30.15585
    perEvtOduflexTcm2Tmp NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCM2 Section Total Monitor Period"
        ::= { optixTrapsPER  15585 }

--  1.3.6.1.4.1.2011.2.25.3.40.40.30.15586
    perEvtOduflexTcm3Uas NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Unavailable Second"
        ::= { optixTrapsPER  15586 }

--  1.3.6.1.4.1.2011.2.25.3.40.40.30.15587
    perEvtOduflexTcm3Sesr NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Ratio of Severely Errored Second"
        ::= { optixTrapsPER  15587 }

--  1.3.6.1.4.1.2011.2.25.3.40.40.30.15588
    perEvtOduflexTcm3Ses NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Severely Errored Second"
        ::= { optixTrapsPER  15588 }

--  1.3.6.1.4.1.2011.2.25.3.40.40.30.15589
    perEvtOduflexTcm3Fees NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Far End Background Block Error"
        ::= { optixTrapsPER  15589 }

--  1.3.6.1.4.1.2011.2.25.3.40.40.30.15590
    perEvtOduflexTcm3Feses NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Far End Severely Errored Second"
        ::= { optixTrapsPER  15590 }

--  1.3.6.1.4.1.2011.2.25.3.40.40.30.15591
    perEvtOduflexTcm3Bber NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Ratio of Background Block Error"
        ::= { optixTrapsPER  15591 }

--  1.3.6.1.4.1.2011.2.25.3.40.40.30.15592
    perEvtOduflexTcm3Febbe NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Far End Background Block Error"
        ::= { optixTrapsPER  15592 }

--  1.3.6.1.4.1.2011.2.25.3.40.40.30.15593
    perEvtOduflexTcm3Febber NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Ratio of Far End Background Block Error"
        ::= { optixTrapsPER  15593 }

--  1.3.6.1.4.1.2011.2.25.3.40.40.30.15594
    perEvtOduflexTcm3Feuas NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Unavailable Second"
        ::= { optixTrapsPER  15594 }

--  1.3.6.1.4.1.2011.2.25.3.40.40.30.15595
    perEvtOduflexTcm3Fesesr NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Ratio of Far End Severely Errored Second"
        ::= { optixTrapsPER  15595 }

--  1.3.6.1.4.1.2011.2.25.3.40.40.30.15596
    perEvtOduflexTcm3Bbe NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Background Block Error"
        ::= { optixTrapsPER  15596 }

--  1.3.6.1.4.1.2011.2.25.3.40.40.30.15597
    perEvtOduflexTcm3Es NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section Errored Second"
        ::= { optixTrapsPER  15597 }

--  1.3.6.1.4.1.2011.2.25.3.40.40.30.15598
    perEvtOduflexTcm3Biaes NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section BIAE Second"
        ::= { optixTrapsPER  15598 }

--  1.3.6.1.4.1.2011.2.25.3.40.40.30.15599
    perEvtOduflexTcm3Iaes NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCMn Section IAE Second"
        ::= { optixTrapsPER  15599 }

--  1.3.6.1.4.1.2011.2.25.3.40.40.30.15600
    perEvtOduflexTcm3Tmp NOTIFICATION-TYPE
        OBJECTS { rptEvtPeriod, rptEvtValue, rptEvtVldty, rptEvtDateTime, rptEvtObjType, rptEvtParaLen, rptEvtPara}
        STATUS current
        DESCRIPTION
        "Trap of PerEvt: ODUFLEX TCM3 Section Total Monitor Period"
        ::= { optixTrapsPER  15600 }

--  1.3.6.1.4.1.2011.2.25.3.40.40.30.15623
    perEvtAmbtempmax NOTIFICATION-TYPE
        OBJECTS { rptEvtPeriod, rptEvtValue, rptEvtVldty, rptEvtDateTime, rptEvtObjType, rptEvtParaLen, rptEvtPara}
        STATUS current
        DESCRIPTION
        "Trap of PerEvt: Maximum subrack ambient temperature"
        ::= { optixTrapsPER  15623 }

--  1.3.6.1.4.1.2011.2.25.3.40.40.30.15624
    perEvtAmbtempmin NOTIFICATION-TYPE
        OBJECTS { rptEvtPeriod, rptEvtValue, rptEvtVldty, rptEvtDateTime, rptEvtObjType, rptEvtParaLen, rptEvtPara}
        STATUS current
        DESCRIPTION
        "Trap of PerEvt: Minimum subrack ambient temperature"
        ::= { optixTrapsPER  15624 }

--  1.3.6.1.4.1.2011.2.25.3.40.40.30.15625
    perEvtAmbtempcur NOTIFICATION-TYPE
        OBJECTS { rptEvtPeriod, rptEvtValue, rptEvtVldty, rptEvtDateTime, rptEvtObjType, rptEvtParaLen, rptEvtPara}
        STATUS current
        DESCRIPTION
        "Trap of PerEvt: Current subrack ambient temperature"
        ::= { optixTrapsPER  15625 }

--  1.3.6.1.4.1.2011.2.25.3.40.40.30.15671
    perEvtMaxsumphaseoffset NOTIFICATION-TYPE
        OBJECTS { rptEvtPeriod, rptEvtValue, rptEvtVldty, rptEvtDateTime, rptEvtObjType, rptEvtParaLen, rptEvtPara}
        STATUS current
        DESCRIPTION
        "Trap of PerEvt: Maximum Value of Time Deviation Sum Between the Master and Slave Clocks Within a Period"
        ::= { optixTrapsPER  15671 }

--  1.3.6.1.4.1.2011.2.25.3.40.40.30.15672
    perEvtMinsumphaseoffset NOTIFICATION-TYPE
        OBJECTS { rptEvtPeriod, rptEvtValue, rptEvtVldty, rptEvtDateTime, rptEvtObjType, rptEvtParaLen, rptEvtPara}
        STATUS current
        DESCRIPTION
        "Trap of PerEvt: Minimum Value of Time Deviation Sum Between the Master and Slave Clocks Within a Period"
        ::= { optixTrapsPER  15672 }

--  1.3.6.1.4.1.2011.2.25.3.40.40.30.15673
    perEvtAvgsumphaseoffset NOTIFICATION-TYPE
        OBJECTS { rptEvtPeriod, rptEvtValue, rptEvtVldty, rptEvtDateTime, rptEvtObjType, rptEvtParaLen, rptEvtPara}
        STATUS current
        DESCRIPTION
        "Trap of PerEvt: Average Value of Time Deviation Sum Between the Master and Slave Clocks Within a Period"
        ::= { optixTrapsPER  15673 }

--  1.3.6.1.4.1.2011.2.25.3.40.40.30.15674
    perEvtQValueEerAver15m NOTIFICATION-TYPE
        OBJECTS { rptEvtPeriod, rptEvtValue, rptEvtVldty, rptEvtDateTime, rptEvtObjType, rptEvtParaLen, rptEvtPara}
        STATUS current
        DESCRIPTION
        "Trap of PerEvt: This performance event shows the average Q value in 15 minutes"
        ::= { optixTrapsPER  15674 }

--  1.3.6.1.4.1.2011.2.25.3.40.40.30.15675
    perEvtQValueEerAver24h NOTIFICATION-TYPE
        OBJECTS { rptEvtPeriod, rptEvtValue, rptEvtVldty, rptEvtDateTime, rptEvtObjType, rptEvtParaLen, rptEvtPara}
        STATUS current
        DESCRIPTION
        "Trap of PerEvt: This performance event shows the average Q value in 24 hours"
        ::= { optixTrapsPER  15675 }

--  1.3.6.1.4.1.2011.2.25.3.40.40.30.15913
    perEvtSdiBbe NOTIFICATION-TYPE
        OBJECTS { rptEvtPeriod, rptEvtValue, rptEvtVldty, rptEvtDateTime, rptEvtObjType, rptEvtParaLen, rptEvtPara}
        STATUS current
        DESCRIPTION
        "Trap of PerEvt: Non-severely errored block count in SDI services"
        ::= { optixTrapsPER  15913 }

--  1.3.6.1.4.1.2011.2.25.3.40.40.30.15914
    perEvtSdiBber NOTIFICATION-TYPE
        OBJECTS { rptEvtPeriod, rptEvtValue, rptEvtVldty, rptEvtDateTime, rptEvtObjType, rptEvtParaLen, rptEvtPara}
        STATUS current
        DESCRIPTION
        "Trap of PerEvt: Ratio of SDI background errored blocks to the total errored blocks (except SES errored blocks)"
        ::= { optixTrapsPER  15914 }

--  1.3.6.1.4.1.2011.2.25.3.40.40.30.15915
    perEvtSdiSesr NOTIFICATION-TYPE
        OBJECTS { rptEvtPeriod, rptEvtValue, rptEvtVldty, rptEvtDateTime, rptEvtObjType, rptEvtParaLen, rptEvtPara}
        STATUS current
        DESCRIPTION
        "Trap of PerEvt: Ratio of severely errored seconds to the total time in SDI services"
        ::= { optixTrapsPER  15915 }

--  1.3.6.1.4.1.2011.2.25.3.40.40.30.15916
    perEvtSdiUas NOTIFICATION-TYPE
        OBJECTS { rptEvtPeriod, rptEvtValue, rptEvtVldty, rptEvtDateTime, rptEvtObjType, rptEvtParaLen, rptEvtPara}
        STATUS current
        DESCRIPTION
        "Trap of PerEvt: Number of seconds during which SDI services are unavailable"
        ::= { optixTrapsPER  15916 }

--  1.3.6.1.4.1.2011.2.25.3.40.40.30.15917
    perEvtSdiEs NOTIFICATION-TYPE
        OBJECTS { rptEvtPeriod, rptEvtValue, rptEvtVldty, rptEvtDateTime, rptEvtObjType, rptEvtParaLen, rptEvtPara}
        STATUS current
        DESCRIPTION
        "Trap of PerEvt: At least one errored block per second in SDI services "
        ::= { optixTrapsPER  15917 }

--  1.3.6.1.4.1.2011.2.25.3.40.40.30.15918
    perEvtSdiSes NOTIFICATION-TYPE
        OBJECTS { rptEvtPeriod, rptEvtValue, rptEvtVldty, rptEvtDateTime, rptEvtObjType, rptEvtParaLen, rptEvtPara}
        STATUS current
        DESCRIPTION
        "Trap of PerEvt: At least 15% errored blocks or one detect block per second in SDI services"
        ::= { optixTrapsPER  15918 }

--  1.3.6.1.4.1.2011.2.25.3.40.40.30.14925
    perEvtQValueEer NOTIFICATION-TYPE
        OBJECTS { rptEvtPeriod, rptEvtValue, rptEvtVldty, rptEvtDateTime, rptEvtObjType, rptEvtParaLen, rptEvtPara}
        STATUS current
        DESCRIPTION
        "Trap of PerEvt: Q_VALUE_EER"
        ::= { optixTrapsPER  14925 }

--  1.3.6.1.4.1.2011.2.25.3.40.40.30.15470
    perEvtOduflexPmTmp  NOTIFICATION-TYPE
        OBJECTS { rptEvtPeriod, rptEvtValue, rptEvtVldty, rptEvtDateTime, rptEvtObjType, rptEvtParaLen, rptEvtPara}
        STATUS current
        DESCRIPTION
        "Trap of PerEvt: ODUFLEX PM Section Total Monitor Period"
        ::= { optixTrapsPER  15470 }






--  1.3.6.1.4.1.2011.2.25.3.40.40.30.118
    perEvtBcvmax NOTIFICATION-TYPE
    OBJECTS { rptEvtPeriod, rptEvtValue, rptEvtVldty, rptEvtDateTime, rptEvtObjType, rptEvtParaLen, rptEvtPara}
    STATUS current
    DESCRIPTION
    "Trap of PerEvt: EDFA Back Current Value Maximum."
    ::= { optixTrapsPER 118 }

--  1.3.6.1.4.1.2011.2.25.3.40.40.30.119
    perEvtBcvmin NOTIFICATION-TYPE
    OBJECTS { rptEvtPeriod, rptEvtValue, rptEvtVldty, rptEvtDateTime, rptEvtObjType, rptEvtParaLen, rptEvtPara}
    STATUS current
    DESCRIPTION
    "Trap of PerEvt: EDFA Back Current Value Minimum."
    ::= { optixTrapsPER 119 }

--  1.3.6.1.4.1.2011.2.25.3.40.40.30.120
    perEvtBcvcur NOTIFICATION-TYPE
    OBJECTS { rptEvtPeriod, rptEvtValue, rptEvtVldty, rptEvtDateTime, rptEvtObjType, rptEvtParaLen, rptEvtPara}
    STATUS current
    DESCRIPTION
    "Trap of PerEvt: EDFA Back Current Value Avg-Value."
    ::= { optixTrapsPER 120 }

--  1.3.6.1.4.1.2011.2.25.3.40.40.30.15074
    perEvtOscBbe NOTIFICATION-TYPE
    OBJECTS { rptEvtPeriod, rptEvtValue, rptEvtVldty, rptEvtDateTime, rptEvtObjType, rptEvtParaLen, rptEvtPara}
    STATUS current
    DESCRIPTION
    "Trap of PerEvt: OSC Path Background Block Error."
    ::= { optixTrapsPER 15074 }

--  1.3.6.1.4.1.2011.2.25.3.40.40.30.15075
    perEvtOscEs NOTIFICATION-TYPE
    OBJECTS { rptEvtPeriod, rptEvtValue, rptEvtVldty, rptEvtDateTime, rptEvtObjType, rptEvtParaLen, rptEvtPara}
    STATUS current
    DESCRIPTION
    "Trap of PerEvt: OSC Path Errored Second."
    ::= { optixTrapsPER 15075 }

--  1.3.6.1.4.1.2011.2.25.3.40.40.30.15076
    perEvtOscSes NOTIFICATION-TYPE
    OBJECTS { rptEvtPeriod, rptEvtValue, rptEvtVldty, rptEvtDateTime, rptEvtObjType, rptEvtParaLen, rptEvtPara}
    STATUS current
    DESCRIPTION
    "Trap of PerEvt: OSC Path Severely Errored Second."
    ::= { optixTrapsPER 15076 }

--  1.3.6.1.4.1.2011.2.25.3.40.40.30.15077
    perEvtOscUas NOTIFICATION-TYPE
    OBJECTS { rptEvtPeriod, rptEvtValue, rptEvtVldty, rptEvtDateTime, rptEvtObjType, rptEvtParaLen, rptEvtPara}
    STATUS current
    DESCRIPTION
    "Trap of PerEvt: OSC Path Unavailable Seconds."
    ::= { optixTrapsPER 15077 }

--  1.3.6.1.4.1.2011.2.25.3.40.40.30.15078
    perEvtOscSesr NOTIFICATION-TYPE
    OBJECTS { rptEvtPeriod, rptEvtValue, rptEvtVldty, rptEvtDateTime, rptEvtObjType, rptEvtParaLen, rptEvtPara}
    STATUS current
    DESCRIPTION
    "Trap of PerEvt: OSC Path Unavailable Seconds."
    ::= { optixTrapsPER 15078 }

--  1.3.6.1.4.1.2011.2.25.3.40.40.30.15079
    perEvtOscBber NOTIFICATION-TYPE
    OBJECTS { rptEvtPeriod, rptEvtValue, rptEvtVldty, rptEvtDateTime, rptEvtObjType, rptEvtParaLen, rptEvtPara}
    STATUS current
    DESCRIPTION
    "Trap of PerEvt: OSC Path Background Block Error Ratio."
    ::= { optixTrapsPER 15079 }

--  1.3.6.1.4.1.2011.2.25.3.40.40.30.15080
    perEvtOscFebbe NOTIFICATION-TYPE
    OBJECTS { rptEvtPeriod, rptEvtValue, rptEvtVldty, rptEvtDateTime, rptEvtObjType, rptEvtParaLen, rptEvtPara}
    STATUS current
    DESCRIPTION
    "Trap of PerEvt: OSC Path Far End Background Block Error."
    ::= { optixTrapsPER 15080 }

--  1.3.6.1.4.1.2011.2.25.3.40.40.30.15081
    perEvtOscFees NOTIFICATION-TYPE
    OBJECTS { rptEvtPeriod, rptEvtValue, rptEvtVldty, rptEvtDateTime, rptEvtObjType, rptEvtParaLen, rptEvtPara}
    STATUS current
    DESCRIPTION
    "Trap of PerEvt: OSC Path Far End Errored Second."
    ::= { optixTrapsPER 15081 }

--  1.3.6.1.4.1.2011.2.25.3.40.40.30.15082
    perEvtOscFeses NOTIFICATION-TYPE
    OBJECTS { rptEvtPeriod, rptEvtValue, rptEvtVldty, rptEvtDateTime, rptEvtObjType, rptEvtParaLen, rptEvtPara}
    STATUS current
    DESCRIPTION
    "Trap of PerEvt: OSC Path Far End Severely Errored Second."
    ::= { optixTrapsPER 15082 }

--  1.3.6.1.4.1.2011.2.25.3.40.40.30.15083
    perEvtOscFeuas NOTIFICATION-TYPE
    OBJECTS { rptEvtPeriod, rptEvtValue, rptEvtVldty, rptEvtDateTime, rptEvtObjType, rptEvtParaLen, rptEvtPara}
    STATUS current
    DESCRIPTION
    "Trap of PerEvt: OSC Path Far End Unavailable Seconds."
    ::= { optixTrapsPER 15083 }

--  1.3.6.1.4.1.2011.2.25.3.40.40.30.15084
    perEvtOscFesesr NOTIFICATION-TYPE
    OBJECTS { rptEvtPeriod, rptEvtValue, rptEvtVldty, rptEvtDateTime, rptEvtObjType, rptEvtParaLen, rptEvtPara}
    STATUS current
    DESCRIPTION
    "Trap of PerEvt: OSC Path Far End Severely Errored Second Ratio."
    ::= { optixTrapsPER 15084 }

--  1.3.6.1.4.1.2011.2.25.3.40.40.30.15085
    perEvtOscFebber NOTIFICATION-TYPE
    OBJECTS { rptEvtPeriod, rptEvtValue, rptEvtVldty, rptEvtDateTime, rptEvtObjType, rptEvtParaLen, rptEvtPara}
    STATUS current
    DESCRIPTION
    "Trap of PerEvt: OSC Path Far End Background Block Error Ratio."
    ::= { optixTrapsPER 15085 }

--  1.3.6.1.4.1.2011.2.25.3.40.40.30.15086
    perEvtOscIaes NOTIFICATION-TYPE
    OBJECTS { rptEvtPeriod, rptEvtValue, rptEvtVldty, rptEvtDateTime, rptEvtObjType, rptEvtParaLen, rptEvtPara}
    STATUS current
    DESCRIPTION
    "Trap of PerEvt: OSC Path Incoming Alignment Errored Second."
    ::= { optixTrapsPER 15086 }

--  1.3.6.1.4.1.2011.2.25.3.40.40.30.15087
    perEvtOscBiaes NOTIFICATION-TYPE
    OBJECTS { rptEvtPeriod, rptEvtValue, rptEvtVldty, rptEvtDateTime, rptEvtObjType, rptEvtParaLen, rptEvtPara}
    STATUS current
    DESCRIPTION
    "Trap of PerEvt: OSC Path Backward Incoming Alignment Errored Second."
    ::= { optixTrapsPER 15087 }

--  1.3.6.1.4.1.2011.2.25.3.40.40.30.15868
    perEvtFswiopmax NOTIFICATION-TYPE
    OBJECTS { rptEvtPeriod, rptEvtValue, rptEvtVldty, rptEvtDateTime, rptEvtObjType, rptEvtParaLen, rptEvtPara}
    STATUS current
    DESCRIPTION
    "Trap of PerEvt: Maximum single-wavelength input optical power."
    ::= { optixTrapsPER 15868 }

--  1.3.6.1.4.1.2011.2.25.3.40.40.30.15869
    perEvtFswiopmin NOTIFICATION-TYPE
    OBJECTS { rptEvtPeriod, rptEvtValue, rptEvtVldty, rptEvtDateTime, rptEvtObjType, rptEvtParaLen, rptEvtPara}
    STATUS current
    DESCRIPTION
    "Trap of PerEvt: Minimum single-wavelength input optical power."
    ::= { optixTrapsPER 15869 }

--  1.3.6.1.4.1.2011.2.25.3.40.40.30.15870
    perEvtFswiopcur NOTIFICATION-TYPE
    OBJECTS { rptEvtPeriod, rptEvtValue, rptEvtVldty, rptEvtDateTime, rptEvtObjType, rptEvtParaLen, rptEvtPara}
    STATUS current
    DESCRIPTION
    "Trap of PerEvt: Current single-wavelength input optical power."
    ::= { optixTrapsPER 15870 }

--  1.3.6.1.4.1.2011.2.25.3.40.40.30.15871
    perEvtFswoopmax NOTIFICATION-TYPE
    OBJECTS { rptEvtPeriod, rptEvtValue, rptEvtVldty, rptEvtDateTime, rptEvtObjType, rptEvtParaLen, rptEvtPara}
    STATUS current
    DESCRIPTION
    "Trap of PerEvt: Maximum single-wavelength output optical power."
    ::= { optixTrapsPER 15871 }

--  1.3.6.1.4.1.2011.2.25.3.40.40.30.15872
    perEvtFswoopmin NOTIFICATION-TYPE
    OBJECTS { rptEvtPeriod, rptEvtValue, rptEvtVldty, rptEvtDateTime, rptEvtObjType, rptEvtParaLen, rptEvtPara}
    STATUS current
    DESCRIPTION
    "Trap of PerEvt: Minimum single-wavelength output optical power."
    ::= { optixTrapsPER 15872 }

--  1.3.6.1.4.1.2011.2.25.3.40.40.30.15873
    perEvtFswoopcur NOTIFICATION-TYPE
    OBJECTS { rptEvtPeriod, rptEvtValue, rptEvtVldty, rptEvtDateTime, rptEvtObjType, rptEvtParaLen, rptEvtPara}
    STATUS current
    DESCRIPTION
    "Trap of PerEvt: Current single-wavelength output optical power."
    ::= { optixTrapsPER 15873 }

--  1.3.6.1.4.1.2011.2.25.3.40.40.30.15880
    perEvtFclsopmax NOTIFICATION-TYPE
    OBJECTS { rptEvtPeriod, rptEvtValue, rptEvtVldty, rptEvtDateTime, rptEvtObjType, rptEvtParaLen, rptEvtPara}
    STATUS current
    DESCRIPTION
    "Trap of PerEvt: Maximum single-channel optical power."
    ::= { optixTrapsPER 15880 }

--  1.3.6.1.4.1.2011.2.25.3.40.40.30.15881
    perEvtFclsopmin NOTIFICATION-TYPE
    OBJECTS { rptEvtPeriod, rptEvtValue, rptEvtVldty, rptEvtDateTime, rptEvtObjType, rptEvtParaLen, rptEvtPara}
    STATUS current
    DESCRIPTION
    "Trap of PerEvt: Minimum  single-channel optical power."
    ::= { optixTrapsPER 15881 }

--  1.3.6.1.4.1.2011.2.25.3.40.40.30.15882
    perEvtFclsopcur NOTIFICATION-TYPE
    OBJECTS { rptEvtPeriod, rptEvtValue, rptEvtVldty, rptEvtDateTime, rptEvtObjType, rptEvtParaLen, rptEvtPara}
    STATUS current
    DESCRIPTION
    "Trap of PerEvt: Current single-channel  input optical power."
    ::= { optixTrapsPER 15882 }

--  1.3.6.1.4.1.2011.2.25.3.40.40.30.15920
    perEvtFpclswlomax NOTIFICATION-TYPE
    OBJECTS { rptEvtPeriod, rptEvtValue, rptEvtVldty, rptEvtDateTime, rptEvtObjType, rptEvtParaLen, rptEvtPara}
    STATUS current
    DESCRIPTION
    "Trap of PerEvt: Maximum Per-Channel Laser WaveLength Offset Value."
    ::= { optixTrapsPER 15920 }

--  1.3.6.1.4.1.2011.2.25.3.40.40.30.15921
    perEvtFpclswlomin NOTIFICATION-TYPE
    OBJECTS { rptEvtPeriod, rptEvtValue, rptEvtVldty, rptEvtDateTime, rptEvtObjType, rptEvtParaLen, rptEvtPara}
    STATUS current
    DESCRIPTION
    "Trap of PerEvt: Minimum Per-Channel Laser WaveLength Offset Value."
    ::= { optixTrapsPER 15921 }

--  1.3.6.1.4.1.2011.2.25.3.40.40.30.15922
    perEvtFpclswlocur NOTIFICATION-TYPE
    OBJECTS { rptEvtPeriod, rptEvtValue, rptEvtVldty, rptEvtDateTime, rptEvtObjType, rptEvtParaLen, rptEvtPara}
    STATUS current
    DESCRIPTION
    "Trap of PerEvt: Current Per-Channel Laser WaveLength Offset Value."
    ::= { optixTrapsPER 15922 }

--  1.3.6.1.4.1.2011.2.25.3.40.40.30.15989
    perEvtOducnTcm1Iaes NOTIFICATION-TYPE
    OBJECTS { rptEvtPeriod, rptEvtValue, rptEvtVldty, rptEvtDateTime, rptEvtObjType, rptEvtParaLen, rptEvtPara}
    STATUS current
    DESCRIPTION
    "Trap of PerEvt: ODUCN TCM1 Incoming Alignment Errored Second."
    ::= { optixTrapsPER 15989 }

--  1.3.6.1.4.1.2011.2.25.3.40.40.30.15990
    perEvtOducnTcm2Iaes NOTIFICATION-TYPE
    OBJECTS { rptEvtPeriod, rptEvtValue, rptEvtVldty, rptEvtDateTime, rptEvtObjType, rptEvtParaLen, rptEvtPara}
    STATUS current
    DESCRIPTION
    "Trap of PerEvt: ODUCN TCM2 Incoming Alignment Errored Second."
    ::= { optixTrapsPER 15990 }

--  1.3.6.1.4.1.2011.2.25.3.40.40.30.15991
    perEvtOducnTcm3Iaes NOTIFICATION-TYPE
    OBJECTS { rptEvtPeriod, rptEvtValue, rptEvtVldty, rptEvtDateTime, rptEvtObjType, rptEvtParaLen, rptEvtPara}
    STATUS current
    DESCRIPTION
    "Trap of PerEvt: ODUCN TCM3 Incoming Alignment Errored Second."
    ::= { optixTrapsPER 15991 }

--  1.3.6.1.4.1.2011.2.25.3.40.40.30.15992
    perEvtOducnTcm4Iaes NOTIFICATION-TYPE
    OBJECTS { rptEvtPeriod, rptEvtValue, rptEvtVldty, rptEvtDateTime, rptEvtObjType, rptEvtParaLen, rptEvtPara}
    STATUS current
    DESCRIPTION
    "Trap of PerEvt: ODUCN TCM4 Incoming Alignment Errored Second."
    ::= { optixTrapsPER 15992 }

--  1.3.6.1.4.1.2011.2.25.3.40.40.30.15993
    perEvtOducnTcm5Iaes NOTIFICATION-TYPE
    OBJECTS { rptEvtPeriod, rptEvtValue, rptEvtVldty, rptEvtDateTime, rptEvtObjType, rptEvtParaLen, rptEvtPara}
    STATUS current
    DESCRIPTION
    "Trap of PerEvt: ODUCN TCM5 Incoming Alignment Errored Second."
    ::= { optixTrapsPER 15993 }

--  1.3.6.1.4.1.2011.2.25.3.40.40.30.15994
    perEvtOducnTcm6Iaes NOTIFICATION-TYPE
    OBJECTS { rptEvtPeriod, rptEvtValue, rptEvtVldty, rptEvtDateTime, rptEvtObjType, rptEvtParaLen, rptEvtPara}
    STATUS current
    DESCRIPTION
    "Trap of PerEvt: ODUCN TCM6 Incoming Alignment Errored Second."
    ::= { optixTrapsPER 15994 }

--  1.3.6.1.4.1.2011.2.25.3.40.40.30.15995
    perEvtOducnTcm1Biaes NOTIFICATION-TYPE
    OBJECTS { rptEvtPeriod, rptEvtValue, rptEvtVldty, rptEvtDateTime, rptEvtObjType, rptEvtParaLen, rptEvtPara}
    STATUS current
    DESCRIPTION
    "Trap of PerEvt: ODUCN TCM1 Backward Incoming Alignment Errored Second."
    ::= { optixTrapsPER 15995 }

--  1.3.6.1.4.1.2011.2.25.3.40.40.30.15996
    perEvtOducnTcm2Biaes NOTIFICATION-TYPE
    OBJECTS { rptEvtPeriod, rptEvtValue, rptEvtVldty, rptEvtDateTime, rptEvtObjType, rptEvtParaLen, rptEvtPara}
    STATUS current
    DESCRIPTION
    "Trap of PerEvt: ODUCN TCM2 Backward Incoming Alignment Errored Second."
    ::= { optixTrapsPER 15996 }

--  1.3.6.1.4.1.2011.2.25.3.40.40.30.15997
    perEvtOducnTcm3Biaes NOTIFICATION-TYPE
    OBJECTS { rptEvtPeriod, rptEvtValue, rptEvtVldty, rptEvtDateTime, rptEvtObjType, rptEvtParaLen, rptEvtPara}
    STATUS current
    DESCRIPTION
    "Trap of PerEvt: ODUCN TCM3 Backward Incoming Alignment Errored Second."
    ::= { optixTrapsPER 15997 }

--  1.3.6.1.4.1.2011.2.25.3.40.40.30.15998
    perEvtOducnTcm4Biaes NOTIFICATION-TYPE
    OBJECTS { rptEvtPeriod, rptEvtValue, rptEvtVldty, rptEvtDateTime, rptEvtObjType, rptEvtParaLen, rptEvtPara}
    STATUS current
    DESCRIPTION
    "Trap of PerEvt: ODUCN TCM4 Backward Incoming Alignment Errored Second."
    ::= { optixTrapsPER 15998 }

--  1.3.6.1.4.1.2011.2.25.3.40.40.30.15999
    perEvtOducnTcm5Biaes NOTIFICATION-TYPE
    OBJECTS { rptEvtPeriod, rptEvtValue, rptEvtVldty, rptEvtDateTime, rptEvtObjType, rptEvtParaLen, rptEvtPara}
    STATUS current
    DESCRIPTION
    "Trap of PerEvt: ODUCN TCM5 Backward Incoming Alignment Errored Second."
    ::= { optixTrapsPER 15999 }

--  1.3.6.1.4.1.2011.2.25.3.40.40.30.16000
    perEvtOducnTcm6Biaes NOTIFICATION-TYPE
    OBJECTS { rptEvtPeriod, rptEvtValue, rptEvtVldty, rptEvtDateTime, rptEvtObjType, rptEvtParaLen, rptEvtPara}
    STATUS current
    DESCRIPTION
    "Trap of PerEvt: ODUCN TCM6 Backward Incoming Alignment Errored Second."
    ::= { optixTrapsPER 16000 }

--  1.3.6.1.4.1.2011.2.25.3.40.40.30.16001
    perEvtOducnTcm1Bbe NOTIFICATION-TYPE
    OBJECTS { rptEvtPeriod, rptEvtValue, rptEvtVldty, rptEvtDateTime, rptEvtObjType, rptEvtParaLen, rptEvtPara}
    STATUS current
    DESCRIPTION
    "Trap of PerEvt: ODUCN TCM1 Background Block Error."
    ::= { optixTrapsPER 16001 }

--  1.3.6.1.4.1.2011.2.25.3.40.40.30.16002
    perEvtOducnTcm2Bbe NOTIFICATION-TYPE
    OBJECTS { rptEvtPeriod, rptEvtValue, rptEvtVldty, rptEvtDateTime, rptEvtObjType, rptEvtParaLen, rptEvtPara}
    STATUS current
    DESCRIPTION
    "Trap of PerEvt: ODUCN TCM2 Background Block Error."
    ::= { optixTrapsPER 16002 }

--  1.3.6.1.4.1.2011.2.25.3.40.40.30.16003
    perEvtOducnTcm3Bbe NOTIFICATION-TYPE
    OBJECTS { rptEvtPeriod, rptEvtValue, rptEvtVldty, rptEvtDateTime, rptEvtObjType, rptEvtParaLen, rptEvtPara}
    STATUS current
    DESCRIPTION
    "Trap of PerEvt: ODUCN TCM3 Background Block Error."
    ::= { optixTrapsPER 16003 }

--  1.3.6.1.4.1.2011.2.25.3.40.40.30.16004
    perEvtOducnTcm4Bbe NOTIFICATION-TYPE
    OBJECTS { rptEvtPeriod, rptEvtValue, rptEvtVldty, rptEvtDateTime, rptEvtObjType, rptEvtParaLen, rptEvtPara}
    STATUS current
    DESCRIPTION
    "Trap of PerEvt: ODUCN TCM4 Background Block Error."
    ::= { optixTrapsPER 16004 }

--  1.3.6.1.4.1.2011.2.25.3.40.40.30.16005
    perEvtOducnTcm5Bbe NOTIFICATION-TYPE
    OBJECTS { rptEvtPeriod, rptEvtValue, rptEvtVldty, rptEvtDateTime, rptEvtObjType, rptEvtParaLen, rptEvtPara}
    STATUS current
    DESCRIPTION
    "Trap of PerEvt: ODUCN TCM5 Background Block Error."
    ::= { optixTrapsPER 16005 }

--  1.3.6.1.4.1.2011.2.25.3.40.40.30.16006
    perEvtOducnTcm6Bbe NOTIFICATION-TYPE
    OBJECTS { rptEvtPeriod, rptEvtValue, rptEvtVldty, rptEvtDateTime, rptEvtObjType, rptEvtParaLen, rptEvtPara}
    STATUS current
    DESCRIPTION
    "Trap of PerEvt: ODUCN TCM6 Background Block Error."
    ::= { optixTrapsPER 16006 }

--  1.3.6.1.4.1.2011.2.25.3.40.40.30.16007
    perEvtOducnTcm1Es NOTIFICATION-TYPE
    OBJECTS { rptEvtPeriod, rptEvtValue, rptEvtVldty, rptEvtDateTime, rptEvtObjType, rptEvtParaLen, rptEvtPara}
    STATUS current
    DESCRIPTION
    "Trap of PerEvt: ODUCN TCM1 Errored Second."
    ::= { optixTrapsPER 16007 }

--  1.3.6.1.4.1.2011.2.25.3.40.40.30.16008
    perEvtOducnTcm2Es NOTIFICATION-TYPE
    OBJECTS { rptEvtPeriod, rptEvtValue, rptEvtVldty, rptEvtDateTime, rptEvtObjType, rptEvtParaLen, rptEvtPara}
    STATUS current
    DESCRIPTION
    "Trap of PerEvt: ODUCN TCM2 Errored Second."
    ::= { optixTrapsPER 16008 }

--  1.3.6.1.4.1.2011.2.25.3.40.40.30.16009
    perEvtOducnTcm3Es NOTIFICATION-TYPE
    OBJECTS { rptEvtPeriod, rptEvtValue, rptEvtVldty, rptEvtDateTime, rptEvtObjType, rptEvtParaLen, rptEvtPara}
    STATUS current
    DESCRIPTION
    "Trap of PerEvt: ODUCN TCM3 Errored Second."
    ::= { optixTrapsPER 16009 }

--  1.3.6.1.4.1.2011.2.25.3.40.40.30.16010
    perEvtOducnTcm4Es NOTIFICATION-TYPE
    OBJECTS { rptEvtPeriod, rptEvtValue, rptEvtVldty, rptEvtDateTime, rptEvtObjType, rptEvtParaLen, rptEvtPara}
    STATUS current
    DESCRIPTION
    "Trap of PerEvt: ODUCN TCM4 Errored Second."
    ::= { optixTrapsPER 16010 }

--  1.3.6.1.4.1.2011.2.25.3.40.40.30.16011
    perEvtOducnTcm5Es NOTIFICATION-TYPE
    OBJECTS { rptEvtPeriod, rptEvtValue, rptEvtVldty, rptEvtDateTime, rptEvtObjType, rptEvtParaLen, rptEvtPara}
    STATUS current
    DESCRIPTION
    "Trap of PerEvt: ODUCN TCM5 Errored Second."
    ::= { optixTrapsPER 16011 }

--  1.3.6.1.4.1.2011.2.25.3.40.40.30.16012
    perEvtOducnTcm6Es NOTIFICATION-TYPE
    OBJECTS { rptEvtPeriod, rptEvtValue, rptEvtVldty, rptEvtDateTime, rptEvtObjType, rptEvtParaLen, rptEvtPara}
    STATUS current
    DESCRIPTION
    "Trap of PerEvt: ODUCN TCM6 Errored Second."
    ::= { optixTrapsPER 16012 }

--  1.3.6.1.4.1.2011.2.25.3.40.40.30.16013
    perEvtOducnTcm1Ses NOTIFICATION-TYPE
    OBJECTS { rptEvtPeriod, rptEvtValue, rptEvtVldty, rptEvtDateTime, rptEvtObjType, rptEvtParaLen, rptEvtPara}
    STATUS current
    DESCRIPTION
    "Trap of PerEvt: ODUCN TCM1 Severely Errored Second."
    ::= { optixTrapsPER 16013 }

--  1.3.6.1.4.1.2011.2.25.3.40.40.30.16014
    perEvtOducnTcm2Ses NOTIFICATION-TYPE
    OBJECTS { rptEvtPeriod, rptEvtValue, rptEvtVldty, rptEvtDateTime, rptEvtObjType, rptEvtParaLen, rptEvtPara}
    STATUS current
    DESCRIPTION
    "Trap of PerEvt: ODUCN TCM2 Severely Errored Second."
    ::= { optixTrapsPER 16014 }

--  1.3.6.1.4.1.2011.2.25.3.40.40.30.16015
    perEvtOducnTcm3Ses NOTIFICATION-TYPE
    OBJECTS { rptEvtPeriod, rptEvtValue, rptEvtVldty, rptEvtDateTime, rptEvtObjType, rptEvtParaLen, rptEvtPara}
    STATUS current
    DESCRIPTION
    "Trap of PerEvt: ODUCN TCM3 Severely Errored Second."
    ::= { optixTrapsPER 16015 }

--  1.3.6.1.4.1.2011.2.25.3.40.40.30.16016
    perEvtOducnTcm4Ses NOTIFICATION-TYPE
    OBJECTS { rptEvtPeriod, rptEvtValue, rptEvtVldty, rptEvtDateTime, rptEvtObjType, rptEvtParaLen, rptEvtPara}
    STATUS current
    DESCRIPTION
    "Trap of PerEvt: ODUCN TCM4 Severely Errored Second."
    ::= { optixTrapsPER 16016 }

--  1.3.6.1.4.1.2011.2.25.3.40.40.30.16017
    perEvtOducnTcm5Ses NOTIFICATION-TYPE
    OBJECTS { rptEvtPeriod, rptEvtValue, rptEvtVldty, rptEvtDateTime, rptEvtObjType, rptEvtParaLen, rptEvtPara}
    STATUS current
    DESCRIPTION
    "Trap of PerEvt: ODUCN TCM5 Severely Errored Second."
    ::= { optixTrapsPER 16017 }

--  1.3.6.1.4.1.2011.2.25.3.40.40.30.16018
    perEvtOducnTcm6Ses NOTIFICATION-TYPE
    OBJECTS { rptEvtPeriod, rptEvtValue, rptEvtVldty, rptEvtDateTime, rptEvtObjType, rptEvtParaLen, rptEvtPara}
    STATUS current
    DESCRIPTION
    "Trap of PerEvt: ODUCN TCM6 Severely Errored Second."
    ::= { optixTrapsPER 16018 }

--  1.3.6.1.4.1.2011.2.25.3.40.40.30.16019
    perEvtOducnTcm1Uas NOTIFICATION-TYPE
    OBJECTS { rptEvtPeriod, rptEvtValue, rptEvtVldty, rptEvtDateTime, rptEvtObjType, rptEvtParaLen, rptEvtPara}
    STATUS current
    DESCRIPTION
    "Trap of PerEvt: ODUCN TCM1 Unavailable Seconds."
    ::= { optixTrapsPER 16019 }

--  1.3.6.1.4.1.2011.2.25.3.40.40.30.16020
    perEvtOducnTcm2Uas NOTIFICATION-TYPE
    OBJECTS { rptEvtPeriod, rptEvtValue, rptEvtVldty, rptEvtDateTime, rptEvtObjType, rptEvtParaLen, rptEvtPara}
    STATUS current
    DESCRIPTION
    "Trap of PerEvt: ODUCN TCM2 Unavailable Seconds."
    ::= { optixTrapsPER 16020 }

--  1.3.6.1.4.1.2011.2.25.3.40.40.30.16021
    perEvtOducnTcm3Uas NOTIFICATION-TYPE
    OBJECTS { rptEvtPeriod, rptEvtValue, rptEvtVldty, rptEvtDateTime, rptEvtObjType, rptEvtParaLen, rptEvtPara}
    STATUS current
    DESCRIPTION
    "Trap of PerEvt: ODUCN TCM3 Unavailable Seconds."
    ::= { optixTrapsPER 16021 }

--  1.3.6.1.4.1.2011.2.25.3.40.40.30.16022
    perEvtOducnTcm4Uas NOTIFICATION-TYPE
    OBJECTS { rptEvtPeriod, rptEvtValue, rptEvtVldty, rptEvtDateTime, rptEvtObjType, rptEvtParaLen, rptEvtPara}
    STATUS current
    DESCRIPTION
    "Trap of PerEvt: ODUCN TCM4 Unavailable Seconds."
    ::= { optixTrapsPER 16022 }

--  1.3.6.1.4.1.2011.2.25.3.40.40.30.16023
    perEvtOducnTcm5Uas NOTIFICATION-TYPE
    OBJECTS { rptEvtPeriod, rptEvtValue, rptEvtVldty, rptEvtDateTime, rptEvtObjType, rptEvtParaLen, rptEvtPara}
    STATUS current
    DESCRIPTION
    "Trap of PerEvt: ODUCN TCM5 Unavailable Seconds."
    ::= { optixTrapsPER 16023 }

--  1.3.6.1.4.1.2011.2.25.3.40.40.30.16024
    perEvtOducnTcm6Uas NOTIFICATION-TYPE
    OBJECTS { rptEvtPeriod, rptEvtValue, rptEvtVldty, rptEvtDateTime, rptEvtObjType, rptEvtParaLen, rptEvtPara}
    STATUS current
    DESCRIPTION
    "Trap of PerEvt: ODUCN TCM6 Unavailable Seconds."
    ::= { optixTrapsPER 16024 }

--  1.3.6.1.4.1.2011.2.25.3.40.40.30.16025
    perEvtOducnTcm1Sesr NOTIFICATION-TYPE
    OBJECTS { rptEvtPeriod, rptEvtValue, rptEvtVldty, rptEvtDateTime, rptEvtObjType, rptEvtParaLen, rptEvtPara}
    STATUS current
    DESCRIPTION
    "Trap of PerEvt: ODUCN TCM1 Severely Errored Second Ratio."
    ::= { optixTrapsPER 16025 }

--  1.3.6.1.4.1.2011.2.25.3.40.40.30.16026
    perEvtOducnTcm2Sesr NOTIFICATION-TYPE
    OBJECTS { rptEvtPeriod, rptEvtValue, rptEvtVldty, rptEvtDateTime, rptEvtObjType, rptEvtParaLen, rptEvtPara}
    STATUS current
    DESCRIPTION
    "Trap of PerEvt: ODUCN TCM2 Severely Errored Second Ratio."
    ::= { optixTrapsPER 16026 }

--  1.3.6.1.4.1.2011.2.25.3.40.40.30.16027
    perEvtOducnTcm3Sesr NOTIFICATION-TYPE
    OBJECTS { rptEvtPeriod, rptEvtValue, rptEvtVldty, rptEvtDateTime, rptEvtObjType, rptEvtParaLen, rptEvtPara}
    STATUS current
    DESCRIPTION
    "Trap of PerEvt: ODUCN TCM3 Severely Errored Second Ratio."
    ::= { optixTrapsPER 16027 }

--  1.3.6.1.4.1.2011.2.25.3.40.40.30.16028
    perEvtOducnTcm4Sesr NOTIFICATION-TYPE
    OBJECTS { rptEvtPeriod, rptEvtValue, rptEvtVldty, rptEvtDateTime, rptEvtObjType, rptEvtParaLen, rptEvtPara}
    STATUS current
    DESCRIPTION
    "Trap of PerEvt: ODUCN TCM4 Severely Errored Second Ratio."
    ::= { optixTrapsPER 16028 }

--  1.3.6.1.4.1.2011.2.25.3.40.40.30.16029
    perEvtOducnTcm5Sesr NOTIFICATION-TYPE
    OBJECTS { rptEvtPeriod, rptEvtValue, rptEvtVldty, rptEvtDateTime, rptEvtObjType, rptEvtParaLen, rptEvtPara}
    STATUS current
    DESCRIPTION
    "Trap of PerEvt: ODUCN TCM5 Severely Errored Second Ratio."
    ::= { optixTrapsPER 16029 }

--  1.3.6.1.4.1.2011.2.25.3.40.40.30.16030
    perEvtOducnTcm6Sesr NOTIFICATION-TYPE
    OBJECTS { rptEvtPeriod, rptEvtValue, rptEvtVldty, rptEvtDateTime, rptEvtObjType, rptEvtParaLen, rptEvtPara}
    STATUS current
    DESCRIPTION
    "Trap of PerEvt: ODUCN TCM6 Severely Errored Second Ratio."
    ::= { optixTrapsPER 16030 }

--  1.3.6.1.4.1.2011.2.25.3.40.40.30.16031
    perEvtOducnTcm1Bber NOTIFICATION-TYPE
    OBJECTS { rptEvtPeriod, rptEvtValue, rptEvtVldty, rptEvtDateTime, rptEvtObjType, rptEvtParaLen, rptEvtPara}
    STATUS current
    DESCRIPTION
    "Trap of PerEvt: ODUCN TCM1 Background Block Error Ratio."
    ::= { optixTrapsPER 16031 }

--  1.3.6.1.4.1.2011.2.25.3.40.40.30.16032
    perEvtOducnTcm2Bber NOTIFICATION-TYPE
    OBJECTS { rptEvtPeriod, rptEvtValue, rptEvtVldty, rptEvtDateTime, rptEvtObjType, rptEvtParaLen, rptEvtPara}
    STATUS current
    DESCRIPTION
    "Trap of PerEvt: ODUCN TCM2 Background Block Error Ratio."
    ::= { optixTrapsPER 16032 }

--  1.3.6.1.4.1.2011.2.25.3.40.40.30.16033
    perEvtOducnTcm3Bber NOTIFICATION-TYPE
    OBJECTS { rptEvtPeriod, rptEvtValue, rptEvtVldty, rptEvtDateTime, rptEvtObjType, rptEvtParaLen, rptEvtPara}
    STATUS current
    DESCRIPTION
    "Trap of PerEvt: ODUCN TCM3 Background Block Error Ratio."
    ::= { optixTrapsPER 16033 }

--  1.3.6.1.4.1.2011.2.25.3.40.40.30.16034
    perEvtOducnTcm4Bber NOTIFICATION-TYPE
    OBJECTS { rptEvtPeriod, rptEvtValue, rptEvtVldty, rptEvtDateTime, rptEvtObjType, rptEvtParaLen, rptEvtPara}
    STATUS current
    DESCRIPTION
    "Trap of PerEvt: ODUCN TCM4 Background Block Error Ratio."
    ::= { optixTrapsPER 16034 }

--  1.3.6.1.4.1.2011.2.25.3.40.40.30.16035
    perEvtOducnTcm5Bber NOTIFICATION-TYPE
    OBJECTS { rptEvtPeriod, rptEvtValue, rptEvtVldty, rptEvtDateTime, rptEvtObjType, rptEvtParaLen, rptEvtPara}
    STATUS current
    DESCRIPTION
    "Trap of PerEvt: ODUCN TCM5 Background Block Error Ratio."
    ::= { optixTrapsPER 16035 }

--  1.3.6.1.4.1.2011.2.25.3.40.40.30.16036
    perEvtOducnTcm6Bber NOTIFICATION-TYPE
    OBJECTS { rptEvtPeriod, rptEvtValue, rptEvtVldty, rptEvtDateTime, rptEvtObjType, rptEvtParaLen, rptEvtPara}
    STATUS current
    DESCRIPTION
    "Trap of PerEvt: ODUCN TCM6 Background Block Error Ratio."
    ::= { optixTrapsPER 16036 }

--  1.3.6.1.4.1.2011.2.25.3.40.40.30.16037
    perEvtOducnTcm1Febbe NOTIFICATION-TYPE
    OBJECTS { rptEvtPeriod, rptEvtValue, rptEvtVldty, rptEvtDateTime, rptEvtObjType, rptEvtParaLen, rptEvtPara}
    STATUS current
    DESCRIPTION
    "Trap of PerEvt: ODUCN TCM1 Far Background Block Error."
    ::= { optixTrapsPER 16037 }

--  1.3.6.1.4.1.2011.2.25.3.40.40.30.16038
    perEvtOducnTcm2Febbe NOTIFICATION-TYPE
    OBJECTS { rptEvtPeriod, rptEvtValue, rptEvtVldty, rptEvtDateTime, rptEvtObjType, rptEvtParaLen, rptEvtPara}
    STATUS current
    DESCRIPTION
    "Trap of PerEvt: ODUCN TCM2 Far Background Block Error."
    ::= { optixTrapsPER 16038 }

--  1.3.6.1.4.1.2011.2.25.3.40.40.30.16039
    perEvtOducnTcm3Febbe NOTIFICATION-TYPE
    OBJECTS { rptEvtPeriod, rptEvtValue, rptEvtVldty, rptEvtDateTime, rptEvtObjType, rptEvtParaLen, rptEvtPara}
    STATUS current
    DESCRIPTION
    "Trap of PerEvt: ODUCN TCM3 Far Background Block Error."
    ::= { optixTrapsPER 16039 }

--  1.3.6.1.4.1.2011.2.25.3.40.40.30.16040
    perEvtOducnTcm4Febbe NOTIFICATION-TYPE
    OBJECTS { rptEvtPeriod, rptEvtValue, rptEvtVldty, rptEvtDateTime, rptEvtObjType, rptEvtParaLen, rptEvtPara}
    STATUS current
    DESCRIPTION
    "Trap of PerEvt: ODUCN TCM4 Far Background Block Error."
    ::= { optixTrapsPER 16040 }

--  1.3.6.1.4.1.2011.2.25.3.40.40.30.16041
    perEvtOducnTcm5Febbe NOTIFICATION-TYPE
    OBJECTS { rptEvtPeriod, rptEvtValue, rptEvtVldty, rptEvtDateTime, rptEvtObjType, rptEvtParaLen, rptEvtPara}
    STATUS current
    DESCRIPTION
    "Trap of PerEvt: ODUCN TCM5 Far Background Block Error."
    ::= { optixTrapsPER 16041 }

--  1.3.6.1.4.1.2011.2.25.3.40.40.30.16042
    perEvtOducnTcm6Febbe NOTIFICATION-TYPE
    OBJECTS { rptEvtPeriod, rptEvtValue, rptEvtVldty, rptEvtDateTime, rptEvtObjType, rptEvtParaLen, rptEvtPara}
    STATUS current
    DESCRIPTION
    "Trap of PerEvt: ODUCN TCM6 Far Background Block Error."
    ::= { optixTrapsPER 16042 }

--  1.3.6.1.4.1.2011.2.25.3.40.40.30.16043
    perEvtOducnTcm1Fees NOTIFICATION-TYPE
    OBJECTS { rptEvtPeriod, rptEvtValue, rptEvtVldty, rptEvtDateTime, rptEvtObjType, rptEvtParaLen, rptEvtPara}
    STATUS current
    DESCRIPTION
    "Trap of PerEvt: ODUCN TCM1 Far Errored Second."
    ::= { optixTrapsPER 16043 }

--  1.3.6.1.4.1.2011.2.25.3.40.40.30.16044
    perEvtOducnTcm2Fees NOTIFICATION-TYPE
    OBJECTS { rptEvtPeriod, rptEvtValue, rptEvtVldty, rptEvtDateTime, rptEvtObjType, rptEvtParaLen, rptEvtPara}
    STATUS current
    DESCRIPTION
    "Trap of PerEvt: ODUCN TCM2 Far Errored Second."
    ::= { optixTrapsPER 16044 }

--  1.3.6.1.4.1.2011.2.25.3.40.40.30.16045
    perEvtOducnTcm3Fees NOTIFICATION-TYPE
    OBJECTS { rptEvtPeriod, rptEvtValue, rptEvtVldty, rptEvtDateTime, rptEvtObjType, rptEvtParaLen, rptEvtPara}
    STATUS current
    DESCRIPTION
    "Trap of PerEvt: ODUCN TCM3 Far Errored Second."
    ::= { optixTrapsPER 16045 }

--  1.3.6.1.4.1.2011.2.25.3.40.40.30.16046
    perEvtOducnTcm4Fees NOTIFICATION-TYPE
    OBJECTS { rptEvtPeriod, rptEvtValue, rptEvtVldty, rptEvtDateTime, rptEvtObjType, rptEvtParaLen, rptEvtPara}
    STATUS current
    DESCRIPTION
    "Trap of PerEvt: ODUCN TCM4 Far Errored Second."
    ::= { optixTrapsPER 16046 }

--  1.3.6.1.4.1.2011.2.25.3.40.40.30.16047
    perEvtOducnTcm5Fees NOTIFICATION-TYPE
    OBJECTS { rptEvtPeriod, rptEvtValue, rptEvtVldty, rptEvtDateTime, rptEvtObjType, rptEvtParaLen, rptEvtPara}
    STATUS current
    DESCRIPTION
    "Trap of PerEvt: ODUCN TCM5 Far Errored Second."
    ::= { optixTrapsPER 16047 }

--  1.3.6.1.4.1.2011.2.25.3.40.40.30.16048
    perEvtOducnTcm6Fees NOTIFICATION-TYPE
    OBJECTS { rptEvtPeriod, rptEvtValue, rptEvtVldty, rptEvtDateTime, rptEvtObjType, rptEvtParaLen, rptEvtPara}
    STATUS current
    DESCRIPTION
    "Trap of PerEvt: ODUCN TCM6 Far Errored Second."
    ::= { optixTrapsPER 16048 }

--  1.3.6.1.4.1.2011.2.25.3.40.40.30.16049
    perEvtOducnTcm1Feses NOTIFICATION-TYPE
    OBJECTS { rptEvtPeriod, rptEvtValue, rptEvtVldty, rptEvtDateTime, rptEvtObjType, rptEvtParaLen, rptEvtPara}
    STATUS current
    DESCRIPTION
    "Trap of PerEvt: ODUCN TCM1 Far Severely Errored Second."
    ::= { optixTrapsPER 16049 }

--  1.3.6.1.4.1.2011.2.25.3.40.40.30.16050
    perEvtOducnTcm2Feses NOTIFICATION-TYPE
    OBJECTS { rptEvtPeriod, rptEvtValue, rptEvtVldty, rptEvtDateTime, rptEvtObjType, rptEvtParaLen, rptEvtPara}
    STATUS current
    DESCRIPTION
    "Trap of PerEvt: ODUCN TCM2 Far Severely Errored Second."
    ::= { optixTrapsPER 16050 }

--  1.3.6.1.4.1.2011.2.25.3.40.40.30.16051
    perEvtOducnTcm3Feses NOTIFICATION-TYPE
    OBJECTS { rptEvtPeriod, rptEvtValue, rptEvtVldty, rptEvtDateTime, rptEvtObjType, rptEvtParaLen, rptEvtPara}
    STATUS current
    DESCRIPTION
    "Trap of PerEvt: ODUCN TCM3 Far Severely Errored Second."
    ::= { optixTrapsPER 16051 }

--  1.3.6.1.4.1.2011.2.25.3.40.40.30.16052
    perEvtOducnTcm4Feses NOTIFICATION-TYPE
    OBJECTS { rptEvtPeriod, rptEvtValue, rptEvtVldty, rptEvtDateTime, rptEvtObjType, rptEvtParaLen, rptEvtPara}
    STATUS current
    DESCRIPTION
    "Trap of PerEvt: ODUCN TCM4 Far Severely Errored Second."
    ::= { optixTrapsPER 16052 }

--  1.3.6.1.4.1.2011.2.25.3.40.40.30.16053
    perEvtOducnTcm5Feses NOTIFICATION-TYPE
    OBJECTS { rptEvtPeriod, rptEvtValue, rptEvtVldty, rptEvtDateTime, rptEvtObjType, rptEvtParaLen, rptEvtPara}
    STATUS current
    DESCRIPTION
    "Trap of PerEvt: ODUCN TCM5 Far Severely Errored Second."
    ::= { optixTrapsPER 16053 }

--  1.3.6.1.4.1.2011.2.25.3.40.40.30.16054
    perEvtOducnTcm6Feses NOTIFICATION-TYPE
    OBJECTS { rptEvtPeriod, rptEvtValue, rptEvtVldty, rptEvtDateTime, rptEvtObjType, rptEvtParaLen, rptEvtPara}
    STATUS current
    DESCRIPTION
    "Trap of PerEvt: ODUCN TCM6 Far Severely Errored Second."
    ::= { optixTrapsPER 16054 }

--  1.3.6.1.4.1.2011.2.25.3.40.40.30.16055
    perEvtOducnTcm1Feuas NOTIFICATION-TYPE
    OBJECTS { rptEvtPeriod, rptEvtValue, rptEvtVldty, rptEvtDateTime, rptEvtObjType, rptEvtParaLen, rptEvtPara}
    STATUS current
    DESCRIPTION
    "Trap of PerEvt: ODUCN TCM1 Far Unavailable Seconds."
    ::= { optixTrapsPER 16055 }

--  1.3.6.1.4.1.2011.2.25.3.40.40.30.16056
    perEvtOducnTcm2Feuas NOTIFICATION-TYPE
    OBJECTS { rptEvtPeriod, rptEvtValue, rptEvtVldty, rptEvtDateTime, rptEvtObjType, rptEvtParaLen, rptEvtPara}
    STATUS current
    DESCRIPTION
    "Trap of PerEvt: ODUCN TCM2 Far Unavailable Seconds."
    ::= { optixTrapsPER 16056 }

--  1.3.6.1.4.1.2011.2.25.3.40.40.30.16057
    perEvtOducnTcm3Feuas NOTIFICATION-TYPE
    OBJECTS { rptEvtPeriod, rptEvtValue, rptEvtVldty, rptEvtDateTime, rptEvtObjType, rptEvtParaLen, rptEvtPara}
    STATUS current
    DESCRIPTION
    "Trap of PerEvt: ODUCN TCM3 Far Unavailable Seconds."
    ::= { optixTrapsPER 16057 }

--  1.3.6.1.4.1.2011.2.25.3.40.40.30.16058
    perEvtOducnTcm4Feuas NOTIFICATION-TYPE
    OBJECTS { rptEvtPeriod, rptEvtValue, rptEvtVldty, rptEvtDateTime, rptEvtObjType, rptEvtParaLen, rptEvtPara}
    STATUS current
    DESCRIPTION
    "Trap of PerEvt: ODUCN TCM4 Far Unavailable Seconds."
    ::= { optixTrapsPER 16058 }

--  1.3.6.1.4.1.2011.2.25.3.40.40.30.16059
    perEvtOducnTcm5Feuas NOTIFICATION-TYPE
    OBJECTS { rptEvtPeriod, rptEvtValue, rptEvtVldty, rptEvtDateTime, rptEvtObjType, rptEvtParaLen, rptEvtPara}
    STATUS current
    DESCRIPTION
    "Trap of PerEvt: ODUCN TCM5 Far Unavailable Seconds."
    ::= { optixTrapsPER 16059 }

--  1.3.6.1.4.1.2011.2.25.3.40.40.30.16060
    perEvtOducnTcm6Feuas NOTIFICATION-TYPE
    OBJECTS { rptEvtPeriod, rptEvtValue, rptEvtVldty, rptEvtDateTime, rptEvtObjType, rptEvtParaLen, rptEvtPara}
    STATUS current
    DESCRIPTION
    "Trap of PerEvt: ODUCN TCM6 Far Unavailable Seconds."
    ::= { optixTrapsPER 16060 }

--  1.3.6.1.4.1.2011.2.25.3.40.40.30.16061
    perEvtOducnTcm1Fesesr NOTIFICATION-TYPE
    OBJECTS { rptEvtPeriod, rptEvtValue, rptEvtVldty, rptEvtDateTime, rptEvtObjType, rptEvtParaLen, rptEvtPara}
    STATUS current
    DESCRIPTION
    "Trap of PerEvt: ODUCN TCM1 Far Severely Errored Second Ratio."
    ::= { optixTrapsPER 16061 }

--  1.3.6.1.4.1.2011.2.25.3.40.40.30.16062
    perEvtOducnTcm2Fesesr NOTIFICATION-TYPE
    OBJECTS { rptEvtPeriod, rptEvtValue, rptEvtVldty, rptEvtDateTime, rptEvtObjType, rptEvtParaLen, rptEvtPara}
    STATUS current
    DESCRIPTION
    "Trap of PerEvt: ODUCN TCM2 Far Severely Errored Second Ratio."
    ::= { optixTrapsPER 16062 }

--  1.3.6.1.4.1.2011.2.25.3.40.40.30.16063
    perEvtOducnTcm3Fesesr NOTIFICATION-TYPE
    OBJECTS { rptEvtPeriod, rptEvtValue, rptEvtVldty, rptEvtDateTime, rptEvtObjType, rptEvtParaLen, rptEvtPara}
    STATUS current
    DESCRIPTION
    "Trap of PerEvt: ODUCN TCM3 Far Severely Errored Second Ratio."
    ::= { optixTrapsPER 16063 }

--  1.3.6.1.4.1.2011.2.25.3.40.40.30.16064
    perEvtOducnTcm4Fesesr NOTIFICATION-TYPE
    OBJECTS { rptEvtPeriod, rptEvtValue, rptEvtVldty, rptEvtDateTime, rptEvtObjType, rptEvtParaLen, rptEvtPara}
    STATUS current
    DESCRIPTION
    "Trap of PerEvt: ODUCN TCM4 Far Severely Errored Second Ratio."
    ::= { optixTrapsPER 16064 }

--  1.3.6.1.4.1.2011.2.25.3.40.40.30.16065
    perEvtOducnTcm5Fesesr NOTIFICATION-TYPE
    OBJECTS { rptEvtPeriod, rptEvtValue, rptEvtVldty, rptEvtDateTime, rptEvtObjType, rptEvtParaLen, rptEvtPara}
    STATUS current
    DESCRIPTION
    "Trap of PerEvt: ODUCN TCM5 Far Severely Errored Second Ratio."
    ::= { optixTrapsPER 16065 }

--  1.3.6.1.4.1.2011.2.25.3.40.40.30.16066
    perEvtOducnTcm6Fesesr NOTIFICATION-TYPE
    OBJECTS { rptEvtPeriod, rptEvtValue, rptEvtVldty, rptEvtDateTime, rptEvtObjType, rptEvtParaLen, rptEvtPara}
    STATUS current
    DESCRIPTION
    "Trap of PerEvt: ODUCN TCM6 Far Severely Errored Second Ratio."
    ::= { optixTrapsPER 16066 }

--  1.3.6.1.4.1.2011.2.25.3.40.40.30.16067
    perEvtOducnTcm1Febber NOTIFICATION-TYPE
    OBJECTS { rptEvtPeriod, rptEvtValue, rptEvtVldty, rptEvtDateTime, rptEvtObjType, rptEvtParaLen, rptEvtPara}
    STATUS current
    DESCRIPTION
    "Trap of PerEvt: ODUCN TCM1 Far Background Block Error Ratio."
    ::= { optixTrapsPER 16067 }

--  1.3.6.1.4.1.2011.2.25.3.40.40.30.16068
    perEvtOducnTcm2Febber NOTIFICATION-TYPE
    OBJECTS { rptEvtPeriod, rptEvtValue, rptEvtVldty, rptEvtDateTime, rptEvtObjType, rptEvtParaLen, rptEvtPara}
    STATUS current
    DESCRIPTION
    "Trap of PerEvt: ODUCN TCM2 Far Background Block Error Ratio."
    ::= { optixTrapsPER 16068 }

--  1.3.6.1.4.1.2011.2.25.3.40.40.30.16069
    perEvtOducnTcm3Febber NOTIFICATION-TYPE
    OBJECTS { rptEvtPeriod, rptEvtValue, rptEvtVldty, rptEvtDateTime, rptEvtObjType, rptEvtParaLen, rptEvtPara}
    STATUS current
    DESCRIPTION
    "Trap of PerEvt: ODUCN TCM3 Far Background Block Error Ratio."
    ::= { optixTrapsPER 16069 }

--  1.3.6.1.4.1.2011.2.25.3.40.40.30.16070
    perEvtOducnTcm4Febber NOTIFICATION-TYPE
    OBJECTS { rptEvtPeriod, rptEvtValue, rptEvtVldty, rptEvtDateTime, rptEvtObjType, rptEvtParaLen, rptEvtPara}
    STATUS current
    DESCRIPTION
    "Trap of PerEvt: ODUCN TCM4 Far Background Block Error Ratio."
    ::= { optixTrapsPER 16070 }

--  1.3.6.1.4.1.2011.2.25.3.40.40.30.16071
    perEvtOducnTcm5Febber NOTIFICATION-TYPE
    OBJECTS { rptEvtPeriod, rptEvtValue, rptEvtVldty, rptEvtDateTime, rptEvtObjType, rptEvtParaLen, rptEvtPara}
    STATUS current
    DESCRIPTION
    "Trap of PerEvt: ODUCN TCM5 Far Background Block Error Ratio."
    ::= { optixTrapsPER 16071 }

--  1.3.6.1.4.1.2011.2.25.3.40.40.30.16072
    perEvtOducnTcm6Febber NOTIFICATION-TYPE
    OBJECTS { rptEvtPeriod, rptEvtValue, rptEvtVldty, rptEvtDateTime, rptEvtObjType, rptEvtParaLen, rptEvtPara}
    STATUS current
    DESCRIPTION
    "Trap of PerEvt: ODUCN TCM6 Far Background Block Error Ratio."
    ::= { optixTrapsPER 16072 }

--  1.3.6.1.4.1.2011.2.25.3.40.40.30.16073
    perEvtOducnTcm1Tmp NOTIFICATION-TYPE
    OBJECTS { rptEvtPeriod, rptEvtValue, rptEvtVldty, rptEvtDateTime, rptEvtObjType, rptEvtParaLen, rptEvtPara}
    STATUS current
    DESCRIPTION
    "Trap of PerEvt: ODUCN TCM1 Section Total Monitor Period."
    ::= { optixTrapsPER 16073 }

--  1.3.6.1.4.1.2011.2.25.3.40.40.30.16074
    perEvtOducnTcm2Tmp NOTIFICATION-TYPE
    OBJECTS { rptEvtPeriod, rptEvtValue, rptEvtVldty, rptEvtDateTime, rptEvtObjType, rptEvtParaLen, rptEvtPara}
    STATUS current
    DESCRIPTION
    "Trap of PerEvt: ODUCN TCM2 Section Total Monitor Period."
    ::= { optixTrapsPER 16074 }

--  1.3.6.1.4.1.2011.2.25.3.40.40.30.16075
    perEvtOducnTcm3Tmp NOTIFICATION-TYPE
    OBJECTS { rptEvtPeriod, rptEvtValue, rptEvtVldty, rptEvtDateTime, rptEvtObjType, rptEvtParaLen, rptEvtPara}
    STATUS current
    DESCRIPTION
    "Trap of PerEvt: ODUCN TCM3 Section Total Monitor Period."
    ::= { optixTrapsPER 16075 }

--  1.3.6.1.4.1.2011.2.25.3.40.40.30.16076
    perEvtOducnTcm4Tmp NOTIFICATION-TYPE
    OBJECTS { rptEvtPeriod, rptEvtValue, rptEvtVldty, rptEvtDateTime, rptEvtObjType, rptEvtParaLen, rptEvtPara}
    STATUS current
    DESCRIPTION
    "Trap of PerEvt: ODUCN TCM4 Section Total Monitor Period."
    ::= { optixTrapsPER 16076 }

--  1.3.6.1.4.1.2011.2.25.3.40.40.30.16077
    perEvtOducnTcm5Tmp NOTIFICATION-TYPE
    OBJECTS { rptEvtPeriod, rptEvtValue, rptEvtVldty, rptEvtDateTime, rptEvtObjType, rptEvtParaLen, rptEvtPara}
    STATUS current
    DESCRIPTION
    "Trap of PerEvt: ODUCN TCM5 Section Total Monitor Period."
    ::= { optixTrapsPER 16077 }

--  1.3.6.1.4.1.2011.2.25.3.40.40.30.16078
    perEvtOducnTcm6Tmp NOTIFICATION-TYPE
    OBJECTS { rptEvtPeriod, rptEvtValue, rptEvtVldty, rptEvtDateTime, rptEvtObjType, rptEvtParaLen, rptEvtPara}
    STATUS current
    DESCRIPTION
    "Trap of PerEvt: ODUCN TCM6 Section Total Monitor Period."
    ::= { optixTrapsPER 16078 }

--  1.3.6.1.4.1.2011.2.25.3.40.40.30.15983
    perEvtLsvolmax NOTIFICATION-TYPE
    OBJECTS { rptEvtPeriod, rptEvtValue, rptEvtVldty, rptEvtDateTime, rptEvtObjType, rptEvtParaLen, rptEvtPara}
    STATUS current
    DESCRIPTION
    "Trap of PerEvt: Maximum laser voltage."
    ::= { optixTrapsPER 15983 }

--  1.3.6.1.4.1.2011.2.25.3.40.40.30.15984
    perEvtLsvolmin NOTIFICATION-TYPE
    OBJECTS { rptEvtPeriod, rptEvtValue, rptEvtVldty, rptEvtDateTime, rptEvtObjType, rptEvtParaLen, rptEvtPara}
    STATUS current
    DESCRIPTION
    "Trap of PerEvt: Minimum laser voltage."
    ::= { optixTrapsPER 15984 }

--  1.3.6.1.4.1.2011.2.25.3.40.40.30.15985
    perEvtLsvolcur NOTIFICATION-TYPE
    OBJECTS { rptEvtPeriod, rptEvtValue, rptEvtVldty, rptEvtDateTime, rptEvtObjType, rptEvtParaLen, rptEvtPara}
    STATUS current
    DESCRIPTION
    "Trap of PerEvt: Current laser voltage."
    ::= { optixTrapsPER 15985 }

--  1.3.6.1.4.1.2011.2.25.3.40.40.30.249
    perEvtIctmpmax NOTIFICATION-TYPE
    OBJECTS { rptEvtPeriod, rptEvtValue, rptEvtVldty, rptEvtDateTime, rptEvtObjType, rptEvtParaLen, rptEvtPara}
    STATUS current
    DESCRIPTION
    "Trap of PerEvt: perEvtIctmpmax."
    ::= { optixTrapsPER 249 }

--  1.3.6.1.4.1.2011.2.25.3.40.40.30.250
    perEvtIctmpmin NOTIFICATION-TYPE
    OBJECTS { rptEvtPeriod, rptEvtValue, rptEvtVldty, rptEvtDateTime, rptEvtObjType, rptEvtParaLen, rptEvtPara}
    STATUS current
    DESCRIPTION
    "Trap of PerEvt: perEvtIctmpmin."
    ::= { optixTrapsPER 250 }

--  1.3.6.1.4.1.2011.2.25.3.40.40.30.251
    perEvtIctmpcur NOTIFICATION-TYPE
    OBJECTS { rptEvtPeriod, rptEvtValue, rptEvtVldty, rptEvtDateTime, rptEvtObjType, rptEvtParaLen, rptEvtPara}
    STATUS current
    DESCRIPTION
    "Trap of PerEvt: perEvtIctmpcur."
    ::= { optixTrapsPER 251 }



--  1.3.6.1.4.1.2011.2.25.3.40.40.30.4172
    perEvtIcclcmax NOTIFICATION-TYPE
    OBJECTS { rptEvtPeriod, rptEvtValue, rptEvtVldty, rptEvtDateTime, rptEvtObjType, rptEvtParaLen, rptEvtPara}
    STATUS current
    DESCRIPTION
    "Trap of PerEvt: perEvtIcclcmax."
    ::= { optixTrapsPER 4172 }

--  1.3.6.1.4.1.2011.2.25.3.40.40.30.4173
    perEvtIcclcmin NOTIFICATION-TYPE
    OBJECTS { rptEvtPeriod, rptEvtValue, rptEvtVldty, rptEvtDateTime, rptEvtObjType, rptEvtParaLen, rptEvtPara}
    STATUS current
    DESCRIPTION
    "Trap of PerEvt: perEvtIcclcmin."
    ::= { optixTrapsPER 4173 }

--  1.3.6.1.4.1.2011.2.25.3.40.40.30.4174
    perEvtIcclccur NOTIFICATION-TYPE
    OBJECTS { rptEvtPeriod, rptEvtValue, rptEvtVldty, rptEvtDateTime, rptEvtObjType, rptEvtParaLen, rptEvtPara}
    STATUS current
    DESCRIPTION
    "Trap of PerEvt: perEvtIcclccur."
    ::= { optixTrapsPER 4174 }

--  1.3.6.1.4.1.2011.2.25.3.40.40.30.16110
    perEvtXcstmpfluct NOTIFICATION-TYPE
    OBJECTS { rptEvtPeriod, rptEvtValue, rptEvtVldty, rptEvtDateTime, rptEvtObjType, rptEvtParaLen, rptEvtPara}
    STATUS current
    DESCRIPTION
    "Trap of PerEvt: Fluctuant value of board temperature."
    ::= { optixTrapsPER 16110 }

--  1.3.6.1.4.1.2011.2.25.3.40.40.30.16111
    perEvtFanspeedmax NOTIFICATION-TYPE
    OBJECTS { rptEvtPeriod, rptEvtValue, rptEvtVldty, rptEvtDateTime, rptEvtObjType, rptEvtParaLen, rptEvtPara}
    STATUS current
    DESCRIPTION
    "Trap of PerEvt: Maximum value of fan speed."
    ::= { optixTrapsPER 16111 }

--  1.3.6.1.4.1.2011.2.25.3.40.40.30.16112
    perEvtFanspeedmin NOTIFICATION-TYPE
    OBJECTS { rptEvtPeriod, rptEvtValue, rptEvtVldty, rptEvtDateTime, rptEvtObjType, rptEvtParaLen, rptEvtPara}
    STATUS current
    DESCRIPTION
    "Trap of PerEvt: Minimum value of fan speed."
    ::= { optixTrapsPER 16112 }

--  1.3.6.1.4.1.2011.2.25.3.40.40.30.16113
    perEvtFanspeedcur NOTIFICATION-TYPE
    OBJECTS { rptEvtPeriod, rptEvtValue, rptEvtVldty, rptEvtDateTime, rptEvtObjType, rptEvtParaLen, rptEvtPara}
    STATUS current
    DESCRIPTION
    "Trap of PerEvt: Current value of fan speed."
    ::= { optixTrapsPER 16113 }

--  1.3.6.1.4.1.2011.2.25.3.40.40.30.16115
    perEvtEsnrmin NOTIFICATION-TYPE
    OBJECTS { rptEvtPeriod, rptEvtValue, rptEvtVldty, rptEvtDateTime, rptEvtObjType, rptEvtParaLen, rptEvtPara}
    STATUS current
    DESCRIPTION
    "Trap of PerEvt: Minimum signal noise ratio."
    ::= { optixTrapsPER 16115 }

--  1.3.6.1.4.1.2011.2.25.3.40.40.30.16116
    perEvtEsnrmax NOTIFICATION-TYPE
    OBJECTS { rptEvtPeriod, rptEvtValue, rptEvtVldty, rptEvtDateTime, rptEvtObjType, rptEvtParaLen, rptEvtPara}
    STATUS current
    DESCRIPTION
    "Trap of PerEvt: Maximum signal noise ratio."
    ::= { optixTrapsPER 16116 }

--  1.3.6.1.4.1.2011.2.25.3.40.40.30.16117
    perEvtEsnrcur NOTIFICATION-TYPE
    OBJECTS { rptEvtPeriod, rptEvtValue, rptEvtVldty, rptEvtDateTime, rptEvtObjType, rptEvtParaLen, rptEvtPara}
    STATUS current
    DESCRIPTION
    "Trap of PerEvt: Current signal noise ratio."
    ::= { optixTrapsPER 16117 }

--  1.3.6.1.4.1.2011.2.25.3.40.40.30.16118
    perEvtEsnravg NOTIFICATION-TYPE
    OBJECTS { rptEvtPeriod, rptEvtValue, rptEvtVldty, rptEvtDateTime, rptEvtObjType, rptEvtParaLen, rptEvtPara}
    STATUS current
    DESCRIPTION
    "Trap of PerEvt: Average signal noise ratio."
    ::= { optixTrapsPER 16118 }

--  1.3.6.1.4.1.2011.2.25.3.40.40.30.16119
    perEvtPdlmax NOTIFICATION-TYPE
    OBJECTS { rptEvtPeriod, rptEvtValue, rptEvtVldty, rptEvtDateTime, rptEvtObjType, rptEvtParaLen, rptEvtPara}
    STATUS current
    DESCRIPTION
    "Trap of PerEvt: Maximum polarization-dependent-loss."
    ::= { optixTrapsPER 16119 }

--  1.3.6.1.4.1.2011.2.25.3.40.40.30.16120
    perEvtPdlmin NOTIFICATION-TYPE
    OBJECTS { rptEvtPeriod, rptEvtValue, rptEvtVldty, rptEvtDateTime, rptEvtObjType, rptEvtParaLen, rptEvtPara}
    STATUS current
    DESCRIPTION
    "Trap of PerEvt: Minimum polarization-dependent-loss."
    ::= { optixTrapsPER 16120 }

--  1.3.6.1.4.1.2011.2.25.3.40.40.30.16121
    perEvtPdlcur NOTIFICATION-TYPE
    OBJECTS { rptEvtPeriod, rptEvtValue, rptEvtVldty, rptEvtDateTime, rptEvtObjType, rptEvtParaLen, rptEvtPara}
    STATUS current
    DESCRIPTION
    "Trap of PerEvt: Current polarization-dependent-loss."
    ::= { optixTrapsPER 16121 }

--  1.3.6.1.4.1.2011.2.25.3.40.40.30.16122
    perEvtPdlavg NOTIFICATION-TYPE
    OBJECTS { rptEvtPeriod, rptEvtValue, rptEvtVldty, rptEvtDateTime, rptEvtObjType, rptEvtParaLen, rptEvtPara}
    STATUS current
    DESCRIPTION
    "Trap of PerEvt: Average polarization-dependent-loss."
    ::= { optixTrapsPER 16122 }

--  1.3.6.1.4.1.2011.2.25.3.40.40.30.16123
    perEvtPmdmax NOTIFICATION-TYPE
    OBJECTS { rptEvtPeriod, rptEvtValue, rptEvtVldty, rptEvtDateTime, rptEvtObjType, rptEvtParaLen, rptEvtPara}
    STATUS current
    DESCRIPTION
    "Trap of PerEvt: Maximum polarization-mode-dispersion."
    ::= { optixTrapsPER 16123 }

--  1.3.6.1.4.1.2011.2.25.3.40.40.30.16124
    perEvtPmdmin NOTIFICATION-TYPE
    OBJECTS { rptEvtPeriod, rptEvtValue, rptEvtVldty, rptEvtDateTime, rptEvtObjType, rptEvtParaLen, rptEvtPara}
    STATUS current
    DESCRIPTION
    "Trap of PerEvt: Minimum polarization-mode-dispersion."
    ::= { optixTrapsPER 16124 }

--  1.3.6.1.4.1.2011.2.25.3.40.40.30.16125
    perEvtPmdcur NOTIFICATION-TYPE
    OBJECTS { rptEvtPeriod, rptEvtValue, rptEvtVldty, rptEvtDateTime, rptEvtObjType, rptEvtParaLen, rptEvtPara}
    STATUS current
    DESCRIPTION
    "Trap of PerEvt: Current polarization-mode-dispersion."
    ::= { optixTrapsPER 16125 }

--  1.3.6.1.4.1.2011.2.25.3.40.40.30.16126
    perEvtPmdavg NOTIFICATION-TYPE
    OBJECTS { rptEvtPeriod, rptEvtValue, rptEvtVldty, rptEvtDateTime, rptEvtObjType, rptEvtParaLen, rptEvtPara}
    STATUS current
    DESCRIPTION
    "Trap of PerEvt: Average polarization-mode-dispersion."
    ::= { optixTrapsPER 16126 }

--  1.3.6.1.4.1.2011.2.25.3.40.40.30.16144
    perEvtQValueEerMin NOTIFICATION-TYPE
    OBJECTS { rptEvtPeriod, rptEvtValue, rptEvtVldty, rptEvtDateTime, rptEvtObjType, rptEvtParaLen, rptEvtPara}
    STATUS current
    DESCRIPTION
    "Trap of PerEvt: Minimum Q data value."
    ::= { optixTrapsPER 16144 }

--  1.3.6.1.4.1.2011.2.25.3.40.40.30.16145
    perEvtQValueEerMax NOTIFICATION-TYPE
    OBJECTS { rptEvtPeriod, rptEvtValue, rptEvtVldty, rptEvtDateTime, rptEvtObjType, rptEvtParaLen, rptEvtPara}
    STATUS current
    DESCRIPTION
    "Trap of PerEvt: Maximun Q data value."
    ::= { optixTrapsPER 16145 }

--  1.3.6.1.4.1.2011.2.25.3.40.40.30.16146
    perEvtBefCorerFloatMin NOTIFICATION-TYPE
    OBJECTS { rptEvtPeriod, rptEvtValue, rptEvtVldty, rptEvtDateTime, rptEvtObjType, rptEvtParaLen, rptEvtPara}
    STATUS current
    DESCRIPTION
    "Trap of PerEvt: Minimum Before FEC Error Correction(Floating point)."
    ::= { optixTrapsPER 16146 }

--  1.3.6.1.4.1.2011.2.25.3.40.40.30.16147
    perEvtBefCorerFloatMax NOTIFICATION-TYPE
    OBJECTS { rptEvtPeriod, rptEvtValue, rptEvtVldty, rptEvtDateTime, rptEvtObjType, rptEvtParaLen, rptEvtPara}
    STATUS current
    DESCRIPTION
    "Trap of PerEvt: Maximum Before FEC Error Correction(Floating point)."
    ::= { optixTrapsPER 16147 }

--  1.3.6.1.4.1.2011.2.25.3.40.40.30.16148
    perEvtAftCorerFloatMax NOTIFICATION-TYPE
    OBJECTS { rptEvtPeriod, rptEvtValue, rptEvtVldty, rptEvtDateTime, rptEvtObjType, rptEvtParaLen, rptEvtPara}
    STATUS current
    DESCRIPTION
    "Trap of PerEvt: Maximum After FEC Error Correction(Floating point)."
    ::= { optixTrapsPER 16148 }

--  1.3.6.1.4.1.2011.2.25.3.40.40.30.16149
    perEvtBefCorerFloatAvr NOTIFICATION-TYPE
    OBJECTS { rptEvtPeriod, rptEvtValue, rptEvtVldty, rptEvtDateTime, rptEvtObjType, rptEvtParaLen, rptEvtPara}
    STATUS current
    DESCRIPTION
    "Trap of PerEvt: Average Before FEC Error Correction(Floating point)."
    ::= { optixTrapsPER 16149 }

--  1.3.6.1.4.1.2011.2.25.3.40.40.30.16150
    perEvtAftCorerFloatAvr NOTIFICATION-TYPE
    OBJECTS { rptEvtPeriod, rptEvtValue, rptEvtVldty, rptEvtDateTime, rptEvtObjType, rptEvtParaLen, rptEvtPara}
    STATUS current
    DESCRIPTION
    "Trap of PerEvt: Average After FEC Error Correction(Floating point)."
    ::= { optixTrapsPER 16150 }

--  1.3.6.1.4.1.2011.2.25.3.40.40.30.16163
    perEvtAftCorerFloatMin NOTIFICATION-TYPE
    OBJECTS { rptEvtPeriod, rptEvtValue, rptEvtVldty, rptEvtDateTime, rptEvtObjType, rptEvtParaLen, rptEvtPara}
    STATUS current
    DESCRIPTION
    "Trap of PerEvt: Minimum After FEC Error Correction(Floating point)."
    ::= { optixTrapsPER 16163 }

--  1.3.6.1.4.1.2011.2.25.3.40.40.30.16171
    perEvtFecCorBitsCnt NOTIFICATION-TYPE
    OBJECTS { rptEvtPeriod, rptEvtValue, rptEvtVldty, rptEvtDateTime, rptEvtObjType, rptEvtParaLen, rptEvtPara}
    STATUS current
    DESCRIPTION
    "Trap of PerEvt: Forward Error Correction - Corrected Bits Count."
    ::= { optixTrapsPER 16171 }

--  1.3.6.1.4.1.2011.2.25.3.40.40.30.16172
    perEvtBdCurPower NOTIFICATION-TYPE
    OBJECTS { rptEvtPeriod, rptEvtValue, rptEvtVldty, rptEvtDateTime, rptEvtObjType, rptEvtParaLen, rptEvtPara}
    STATUS current
    DESCRIPTION
    "Trap of PerEvt: Real-Time Board Power Consumption."
    ::= { optixTrapsPER 16172 }



--  1.3.6.1.4.1.2011.2.25.3.40.40.30.16114
    perEvtFanspeedfluct NOTIFICATION-TYPE
    OBJECTS { rptEvtPeriod, rptEvtValue, rptEvtVldty, rptEvtDateTime, rptEvtObjType, rptEvtParaLen, rptEvtPara}
    STATUS current
    DESCRIPTION
    "Trap of PerEvt: Fluctuant value of fan speed."
    ::= { optixTrapsPER 16114 }
	--  1.3.6.1.4.1.2011.2.25.3.40.40.30.16174
    perEvtInputvoltmax NOTIFICATION-TYPE
    OBJECTS { rptEvtPeriod, rptEvtValue, rptEvtVldty, rptEvtDateTime, rptEvtObjType, rptEvtParaLen, rptEvtPara}
    STATUS current
    DESCRIPTION
    "Trap of PerEvt: Maximum input voltagevoltage."
    ::= { optixTrapsPER 16174 }

--  1.3.6.1.4.1.2011.2.25.3.40.40.30.16175
    perEvtInputvoltcur NOTIFICATION-TYPE
    OBJECTS { rptEvtPeriod, rptEvtValue, rptEvtVldty, rptEvtDateTime, rptEvtObjType, rptEvtParaLen, rptEvtPara}
    STATUS current
    DESCRIPTION
    "Trap of PerEvt: current input voltage."
    ::= { optixTrapsPER 16175 }

--  1.3.6.1.4.1.2011.2.25.3.40.40.30.16176
    perEvtInputvoltmin NOTIFICATION-TYPE
    OBJECTS { rptEvtPeriod, rptEvtValue, rptEvtVldty, rptEvtDateTime, rptEvtObjType, rptEvtParaLen, rptEvtPara}
    STATUS current
    DESCRIPTION
    "Trap of PerEvt: Minimum input voltage."
    ::= { optixTrapsPER 16176 }

--  1.3.6.1.4.1.2011.2.25.3.40.40.30.16177
    perEvtOutputvoltmax NOTIFICATION-TYPE
    OBJECTS { rptEvtPeriod, rptEvtValue, rptEvtVldty, rptEvtDateTime, rptEvtObjType, rptEvtParaLen, rptEvtPara}
    STATUS current
    DESCRIPTION
    "Trap of PerEvt: Maximum output voltage."
    ::= { optixTrapsPER 16177 }

--  1.3.6.1.4.1.2011.2.25.3.40.40.30.16178
    perEvtOutputvoltcur NOTIFICATION-TYPE
    OBJECTS { rptEvtPeriod, rptEvtValue, rptEvtVldty, rptEvtDateTime, rptEvtObjType, rptEvtParaLen, rptEvtPara}
    STATUS current
    DESCRIPTION
    "Trap of PerEvt: Current output voltage."
    ::= { optixTrapsPER 16178 }

--  1.3.6.1.4.1.2011.2.25.3.40.40.30.16179
    perEvtOutputvoltmin NOTIFICATION-TYPE
    OBJECTS { rptEvtPeriod, rptEvtValue, rptEvtVldty, rptEvtDateTime, rptEvtObjType, rptEvtParaLen, rptEvtPara}
    STATUS current
    DESCRIPTION
    "Trap of PerEvt: Minimum output voltage."
    ::= { optixTrapsPER 16179 }

--  1.3.6.1.4.1.2011.2.25.3.40.40.30.16180
    perEvtOutputcurrentmax NOTIFICATION-TYPE
    OBJECTS { rptEvtPeriod, rptEvtValue, rptEvtVldty, rptEvtDateTime, rptEvtObjType, rptEvtParaLen, rptEvtPara}
    STATUS current
    DESCRIPTION
    "Trap of PerEvt: Maximum output current."
    ::= { optixTrapsPER 16180 }

--  1.3.6.1.4.1.2011.2.25.3.40.40.30.16181
    perEvtOutputcurrentcur NOTIFICATION-TYPE
    OBJECTS { rptEvtPeriod, rptEvtValue, rptEvtVldty, rptEvtDateTime, rptEvtObjType, rptEvtParaLen, rptEvtPara}
    STATUS current
    DESCRIPTION
    "Trap of PerEvt: Current output current."
    ::= { optixTrapsPER 16181 }

--  1.3.6.1.4.1.2011.2.25.3.40.40.30.16182
    perEvtOutputcurrentmin NOTIFICATION-TYPE
    OBJECTS { rptEvtPeriod, rptEvtValue, rptEvtVldty, rptEvtDateTime, rptEvtObjType, rptEvtParaLen, rptEvtPara}
    STATUS current
    DESCRIPTION
    "Trap of PerEvt: Minimum output current."
    ::= { optixTrapsPER 16182 }

--  1.3.6.1.4.1.2011.2.25.3.40.40.30.16183
    perEvtInputcurrentmax NOTIFICATION-TYPE
    OBJECTS { rptEvtPeriod, rptEvtValue, rptEvtVldty, rptEvtDateTime, rptEvtObjType, rptEvtParaLen, rptEvtPara}
    STATUS current
    DESCRIPTION
    "Trap of PerEvt: Maximum input current."
    ::= { optixTrapsPER 16183 }

--  1.3.6.1.4.1.2011.2.25.3.40.40.30.16184
    perEvtInputcurrentcur NOTIFICATION-TYPE
    OBJECTS { rptEvtPeriod, rptEvtValue, rptEvtVldty, rptEvtDateTime, rptEvtObjType, rptEvtParaLen, rptEvtPara}
    STATUS current
    DESCRIPTION
    "Trap of PerEvt: Current input current."
    ::= { optixTrapsPER 16184 }

--  1.3.6.1.4.1.2011.2.25.3.40.40.30.16185
    perEvtInputcurrentmin NOTIFICATION-TYPE
    OBJECTS { rptEvtPeriod, rptEvtValue, rptEvtVldty, rptEvtDateTime, rptEvtObjType, rptEvtParaLen, rptEvtPara}
    STATUS current
    DESCRIPTION
    "Trap of PerEvt: Minimum input current."
    ::= { optixTrapsPER 16185 }

--  1.3.6.1.4.1.2011.2.25.3.40.40.30.16186
    perEvtLswfrequency NOTIFICATION-TYPE
    OBJECTS { rptEvtPeriod, rptEvtValue, rptEvtVldty, rptEvtDateTime, rptEvtObjType, rptEvtParaLen, rptEvtPara}
    STATUS current
    DESCRIPTION
    "Trap of PerEvt: Central frequency of a wavelength."
    ::= { optixTrapsPER 16186 }


--  1.3.6.1.4.1.2011.2.25.3.40.40.30.14919
    perEvtCpuusagemax NOTIFICATION-TYPE
        OBJECTS { rptEvtPeriod, rptEvtValue, rptEvtVldty, rptEvtDateTime, rptEvtObjType, rptEvtParaLen, rptEvtPara}
        STATUS current
        DESCRIPTION
        "Trap of PerEvt: Maximum value of CPU usage"
        ::= { optixTrapsPER  14919 }

--  1.3.6.1.4.1.2011.2.25.3.40.40.30.14920
    perEvtCpuusagemin NOTIFICATION-TYPE
        OBJECTS { rptEvtPeriod, rptEvtValue, rptEvtVldty, rptEvtDateTime, rptEvtObjType, rptEvtParaLen, rptEvtPara}
        STATUS current
        DESCRIPTION
        "Trap of PerEvt: Minimum value of CPU usage"
        ::= { optixTrapsPER  14920 }

--  1.3.6.1.4.1.2011.2.25.3.40.40.30.14921
    perEvtCpuusagecur NOTIFICATION-TYPE
        OBJECTS { rptEvtPeriod, rptEvtValue, rptEvtVldty, rptEvtDateTime, rptEvtObjType, rptEvtParaLen, rptEvtPara}
        STATUS current
        DESCRIPTION
        "Trap of PerEvt: Current value of CPU usage"
        ::= { optixTrapsPER  14921 }

--  1.3.6.1.4.1.2011.2.25.3.40.40.30.16230
    perEvtTduflexSes NOTIFICATION-TYPE
    OBJECTS { rptEvtPeriod, rptEvtValue, rptEvtVldty, rptEvtDateTime, rptEvtObjType, rptEvtParaLen, rptEvtPara}
    STATUS current
    DESCRIPTION
    "Trap of PerEvt: TDUflex Severely Errored Second."
    ::= { optixTrapsPER 16230 }

--  1.3.6.1.4.1.2011.2.25.3.40.40.30.16231
    perEvtTduflexUas NOTIFICATION-TYPE
    OBJECTS { rptEvtPeriod, rptEvtValue, rptEvtVldty, rptEvtDateTime, rptEvtObjType, rptEvtParaLen, rptEvtPara}
    STATUS current
    DESCRIPTION
    "Trap of PerEvt: TDUflex Unavailable Second."
    ::= { optixTrapsPER 16231 }

--  1.3.6.1.4.1.2011.2.25.3.40.40.30.16232
    perEvtTduflexTmp NOTIFICATION-TYPE
    OBJECTS { rptEvtPeriod, rptEvtValue, rptEvtVldty, rptEvtDateTime, rptEvtObjType, rptEvtParaLen, rptEvtPara}
    STATUS current
    DESCRIPTION
    "Trap of PerEvt: Total monitoring period of the TDUflex."
    ::= { optixTrapsPER 16232 }

--  1.3.6.1.4.1.2011.2.25.3.40.40.30.16236
    perEvtMemoccupymax NOTIFICATION-TYPE
    OBJECTS { rptEvtPeriod, rptEvtValue, rptEvtVldty, rptEvtDateTime, rptEvtObjType, rptEvtParaLen, rptEvtPara}
    STATUS current
    DESCRIPTION
    "Trap of PerEvt: Maximum number of bytes used in the memory."
    ::= { optixTrapsPER 16236 }

--  1.3.6.1.4.1.2011.2.25.3.40.40.30.16237
    perEvtMemoccupymin NOTIFICATION-TYPE
    OBJECTS { rptEvtPeriod, rptEvtValue, rptEvtVldty, rptEvtDateTime, rptEvtObjType, rptEvtParaLen, rptEvtPara}
    STATUS current
    DESCRIPTION
    "Trap of PerEvt: Minimum number of bytes used in the memory."
    ::= { optixTrapsPER 16237 }

--  1.3.6.1.4.1.2011.2.25.3.40.40.30.16239
    perEvtMemoccupycur NOTIFICATION-TYPE
    OBJECTS { rptEvtPeriod, rptEvtValue, rptEvtVldty, rptEvtDateTime, rptEvtObjType, rptEvtParaLen, rptEvtPara}
    STATUS current
    DESCRIPTION
    "Trap of PerEvt: Current number of bytes used in the memory."
    ::= { optixTrapsPER 16239 }

--  1.3.6.1.4.1.2011.2.25.3.40.40.30.16240
    perEvtOutputpowercur NOTIFICATION-TYPE
    OBJECTS { rptEvtPeriod, rptEvtValue, rptEvtVldty, rptEvtDateTime, rptEvtObjType, rptEvtParaLen, rptEvtPara}
    STATUS current
    DESCRIPTION
    "Trap of PerEvt: Current output power."
    ::= { optixTrapsPER 16240 }

--  1.3.6.1.4.1.2011.2.25.3.40.40.30.16242
    perEvtCpuperformance NOTIFICATION-TYPE
    OBJECTS { rptEvtPeriod, rptEvtValue, rptEvtVldty, rptEvtDateTime, rptEvtObjType, rptEvtParaLen, rptEvtPara}
    STATUS current
    DESCRIPTION
    "Trap of PerEvt: Usage of each CPU in a board."
    ::= { optixTrapsPER 16242 }

--  1.3.6.1.4.1.2011.2.25.3.40.40.30.16243
    perEvtOtu25Bbe NOTIFICATION-TYPE
    OBJECTS { rptEvtPeriod, rptEvtValue, rptEvtVldty, rptEvtDateTime, rptEvtObjType, rptEvtParaLen, rptEvtPara}
    STATUS current
    DESCRIPTION
    "Trap of PerEvt: OTU25 SM Background Block Error."
    ::= { optixTrapsPER 16243 }

--  1.3.6.1.4.1.2011.2.25.3.40.40.30.16244
    perEvtOtu25Fees NOTIFICATION-TYPE
    OBJECTS { rptEvtPeriod, rptEvtValue, rptEvtVldty, rptEvtDateTime, rptEvtObjType, rptEvtParaLen, rptEvtPara}
    STATUS current
    DESCRIPTION
    "Trap of PerEvt: OTU25 SM Far Errored Second."
    ::= { optixTrapsPER 16244 }

--  1.3.6.1.4.1.2011.2.25.3.40.40.30.16245
    perEvtOtu25Febbe NOTIFICATION-TYPE
    OBJECTS { rptEvtPeriod, rptEvtValue, rptEvtVldty, rptEvtDateTime, rptEvtObjType, rptEvtParaLen, rptEvtPara}
    STATUS current
    DESCRIPTION
    "Trap of PerEvt: OTU25 SM Far Background Block Error."
    ::= { optixTrapsPER 16245 }

--  1.3.6.1.4.1.2011.2.25.3.40.40.30.16246
    perEvtOtu25Bber NOTIFICATION-TYPE
    OBJECTS { rptEvtPeriod, rptEvtValue, rptEvtVldty, rptEvtDateTime, rptEvtObjType, rptEvtParaLen, rptEvtPara}
    STATUS current
    DESCRIPTION
    "Trap of PerEvt: OTU25 SM Background Block Error Ratio."
    ::= { optixTrapsPER 16246 }

--  1.3.6.1.4.1.2011.2.25.3.40.40.30.16247
    perEvtOtu25Sesr NOTIFICATION-TYPE
    OBJECTS { rptEvtPeriod, rptEvtValue, rptEvtVldty, rptEvtDateTime, rptEvtObjType, rptEvtParaLen, rptEvtPara}
    STATUS current
    DESCRIPTION
    "Trap of PerEvt: OTU25 SM Severely Errored Second Ratio."
    ::= { optixTrapsPER 16247 }

--  1.3.6.1.4.1.2011.2.25.3.40.40.30.16248
    perEvtOtu25Feses NOTIFICATION-TYPE
    OBJECTS { rptEvtPeriod, rptEvtValue, rptEvtVldty, rptEvtDateTime, rptEvtObjType, rptEvtParaLen, rptEvtPara}
    STATUS current
    DESCRIPTION
    "Trap of PerEvt: OTU25 SM Far Severely Errored Second."
    ::= { optixTrapsPER 16248 }

--  1.3.6.1.4.1.2011.2.25.3.40.40.30.16249
    perEvtOtu25Biaes NOTIFICATION-TYPE
    OBJECTS { rptEvtPeriod, rptEvtValue, rptEvtVldty, rptEvtDateTime, rptEvtObjType, rptEvtParaLen, rptEvtPara}
    STATUS current
    DESCRIPTION
    "Trap of PerEvt: OTU25 SM Backward Incoming Alignment Errored Second."
    ::= { optixTrapsPER 16249 }

--  1.3.6.1.4.1.2011.2.25.3.40.40.30.16250
    perEvtOtu25Uas NOTIFICATION-TYPE
    OBJECTS { rptEvtPeriod, rptEvtValue, rptEvtVldty, rptEvtDateTime, rptEvtObjType, rptEvtParaLen, rptEvtPara}
    STATUS current
    DESCRIPTION
    "Trap of PerEvt: OTU25 SM Unavailable Seconds."
    ::= { optixTrapsPER 16250 }

--  1.3.6.1.4.1.2011.2.25.3.40.40.30.16251
    perEvtOtu25Ses NOTIFICATION-TYPE
    OBJECTS { rptEvtPeriod, rptEvtValue, rptEvtVldty, rptEvtDateTime, rptEvtObjType, rptEvtParaLen, rptEvtPara}
    STATUS current
    DESCRIPTION
    "Trap of PerEvt: OTU25 SM Severely Errored Second."
    ::= { optixTrapsPER 16251 }

--  1.3.6.1.4.1.2011.2.25.3.40.40.30.16252
    perEvtOtu25Es NOTIFICATION-TYPE
    OBJECTS { rptEvtPeriod, rptEvtValue, rptEvtVldty, rptEvtDateTime, rptEvtObjType, rptEvtParaLen, rptEvtPara}
    STATUS current
    DESCRIPTION
    "Trap of PerEvt: OTU25 SM Errored Second."
    ::= { optixTrapsPER 16252 }

--  1.3.6.1.4.1.2011.2.25.3.40.40.30.16253
    perEvtOtu25Iaes NOTIFICATION-TYPE
    OBJECTS { rptEvtPeriod, rptEvtValue, rptEvtVldty, rptEvtDateTime, rptEvtObjType, rptEvtParaLen, rptEvtPara}
    STATUS current
    DESCRIPTION
    "Trap of PerEvt: OTU25 SM Incoming Alignment Errored Second."
    ::= { optixTrapsPER 16253 }

--  1.3.6.1.4.1.2011.2.25.3.40.40.30.16254
    perEvtOtu25Febber NOTIFICATION-TYPE
    OBJECTS { rptEvtPeriod, rptEvtValue, rptEvtVldty, rptEvtDateTime, rptEvtObjType, rptEvtParaLen, rptEvtPara}
    STATUS current
    DESCRIPTION
    "Trap of PerEvt: OTU25 SM Far Background Block Error Ratio."
    ::= { optixTrapsPER 16254 }

--  1.3.6.1.4.1.2011.2.25.3.40.40.30.16255
    perEvtOtu25Feuas NOTIFICATION-TYPE
    OBJECTS { rptEvtPeriod, rptEvtValue, rptEvtVldty, rptEvtDateTime, rptEvtObjType, rptEvtParaLen, rptEvtPara}
    STATUS current
    DESCRIPTION
    "Trap of PerEvt: OTU25 SM Far Unavailable Seconds."
    ::= { optixTrapsPER 16255 }

--  1.3.6.1.4.1.2011.2.25.3.40.40.30.16256
    perEvtOtu25Tmp NOTIFICATION-TYPE
    OBJECTS { rptEvtPeriod, rptEvtValue, rptEvtVldty, rptEvtDateTime, rptEvtObjType, rptEvtParaLen, rptEvtPara}
    STATUS current
    DESCRIPTION
    "Trap of PerEvt: OTU25 Total Monitor Period."
    ::= { optixTrapsPER 16256 }

--  1.3.6.1.4.1.2011.2.25.3.40.40.30.16257
    perEvtOtu25Fesesr NOTIFICATION-TYPE
    OBJECTS { rptEvtPeriod, rptEvtValue, rptEvtVldty, rptEvtDateTime, rptEvtObjType, rptEvtParaLen, rptEvtPara}
    STATUS current
    DESCRIPTION
    "Trap of PerEvt: OTU25 SM Far Severely Errored Second Ratio."
    ::= { optixTrapsPER 16257 }

--  1.3.6.1.4.1.2011.2.25.3.40.40.30.16258
    perEvtOdu25PmFesesr NOTIFICATION-TYPE
    OBJECTS { rptEvtPeriod, rptEvtValue, rptEvtVldty, rptEvtDateTime, rptEvtObjType, rptEvtParaLen, rptEvtPara}
    STATUS current
    DESCRIPTION
    "Trap of PerEvt: ODU25 PM Far Severely Errored Second Ratio."
    ::= { optixTrapsPER 16258 }

--  1.3.6.1.4.1.2011.2.25.3.40.40.30.16259
    perEvtOdu25PmFebber NOTIFICATION-TYPE
    OBJECTS { rptEvtPeriod, rptEvtValue, rptEvtVldty, rptEvtDateTime, rptEvtObjType, rptEvtParaLen, rptEvtPara}
    STATUS current
    DESCRIPTION
    "Trap of PerEvt: ODU25 PM Far Background Block Error Ratio."
    ::= { optixTrapsPER 16259 }

--  1.3.6.1.4.1.2011.2.25.3.40.40.30.16260
    perEvtOdu25PmFees NOTIFICATION-TYPE
    OBJECTS { rptEvtPeriod, rptEvtValue, rptEvtVldty, rptEvtDateTime, rptEvtObjType, rptEvtParaLen, rptEvtPara}
    STATUS current
    DESCRIPTION
    "Trap of PerEvt: ODU25 PM Far Errored Second."
    ::= { optixTrapsPER 16260 }

--  1.3.6.1.4.1.2011.2.25.3.40.40.30.16261
    perEvtOdu25PmFeses NOTIFICATION-TYPE
    OBJECTS { rptEvtPeriod, rptEvtValue, rptEvtVldty, rptEvtDateTime, rptEvtObjType, rptEvtParaLen, rptEvtPara}
    STATUS current
    DESCRIPTION
    "Trap of PerEvt: ODU25 PM Far Severely Errored Second."
    ::= { optixTrapsPER 16261 }

--  1.3.6.1.4.1.2011.2.25.3.40.40.30.16262
    perEvtOdu25PmFeuas NOTIFICATION-TYPE
    OBJECTS { rptEvtPeriod, rptEvtValue, rptEvtVldty, rptEvtDateTime, rptEvtObjType, rptEvtParaLen, rptEvtPara}
    STATUS current
    DESCRIPTION
    "Trap of PerEvt: ODU25 PM Far Unavailable Seconds."
    ::= { optixTrapsPER 16262 }

--  1.3.6.1.4.1.2011.2.25.3.40.40.30.16263
    perEvtOdu25PmEs NOTIFICATION-TYPE
    OBJECTS { rptEvtPeriod, rptEvtValue, rptEvtVldty, rptEvtDateTime, rptEvtObjType, rptEvtParaLen, rptEvtPara}
    STATUS current
    DESCRIPTION
    "Trap of PerEvt: ODU25 PM Errored Second."
    ::= { optixTrapsPER 16263 }

--  1.3.6.1.4.1.2011.2.25.3.40.40.30.16264
    perEvtOdu25PmSes NOTIFICATION-TYPE
    OBJECTS { rptEvtPeriod, rptEvtValue, rptEvtVldty, rptEvtDateTime, rptEvtObjType, rptEvtParaLen, rptEvtPara}
    STATUS current
    DESCRIPTION
    "Trap of PerEvt: ODU25 PM Severely Errored Second."
    ::= { optixTrapsPER 16264 }

--  1.3.6.1.4.1.2011.2.25.3.40.40.30.16265
    perEvtOdu25PmBbe NOTIFICATION-TYPE
    OBJECTS { rptEvtPeriod, rptEvtValue, rptEvtVldty, rptEvtDateTime, rptEvtObjType, rptEvtParaLen, rptEvtPara}
    STATUS current
    DESCRIPTION
    "Trap of PerEvt: ODU25 PM Background Block Error."
    ::= { optixTrapsPER 16265 }

--  1.3.6.1.4.1.2011.2.25.3.40.40.30.16266
    perEvtOdu25PmBber NOTIFICATION-TYPE
    OBJECTS { rptEvtPeriod, rptEvtValue, rptEvtVldty, rptEvtDateTime, rptEvtObjType, rptEvtParaLen, rptEvtPara}
    STATUS current
    DESCRIPTION
    "Trap of PerEvt: ODU25 PM Background Block Error Ratio."
    ::= { optixTrapsPER 16266 }

--  1.3.6.1.4.1.2011.2.25.3.40.40.30.16267
    perEvtOdu25PmFebbe NOTIFICATION-TYPE
    OBJECTS { rptEvtPeriod, rptEvtValue, rptEvtVldty, rptEvtDateTime, rptEvtObjType, rptEvtParaLen, rptEvtPara}
    STATUS current
    DESCRIPTION
    "Trap of PerEvt: ODU25 PM Far Background Block Error."
    ::= { optixTrapsPER 16267 }

--  1.3.6.1.4.1.2011.2.25.3.40.40.30.16268
    perEvtOdu25PmUas NOTIFICATION-TYPE
    OBJECTS { rptEvtPeriod, rptEvtValue, rptEvtVldty, rptEvtDateTime, rptEvtObjType, rptEvtParaLen, rptEvtPara}
    STATUS current
    DESCRIPTION
    "Trap of PerEvt: ODU25 PM Unavailable Seconds."
    ::= { optixTrapsPER 16268 }

--  1.3.6.1.4.1.2011.2.25.3.40.40.30.16269
    perEvtOdu25PmSesr NOTIFICATION-TYPE
    OBJECTS { rptEvtPeriod, rptEvtValue, rptEvtVldty, rptEvtDateTime, rptEvtObjType, rptEvtParaLen, rptEvtPara}
    STATUS current
    DESCRIPTION
    "Trap of PerEvt: ODU25 PM Severely Errored Second Ratio."
    ::= { optixTrapsPER 16269 }

--  1.3.6.1.4.1.2011.2.25.3.40.40.30.16270
    perEvtOdu25PmTmp NOTIFICATION-TYPE
    OBJECTS { rptEvtPeriod, rptEvtValue, rptEvtVldty, rptEvtDateTime, rptEvtObjType, rptEvtParaLen, rptEvtPara}
    STATUS current
    DESCRIPTION
    "Trap of PerEvt: ODU25 PM Section Total Monitor Period."
    ::= { optixTrapsPER 16270 }

--  1.3.6.1.4.1.2011.2.25.3.40.40.30.16271
    perEvtOdu25Tcm1Iaes NOTIFICATION-TYPE
    OBJECTS { rptEvtPeriod, rptEvtValue, rptEvtVldty, rptEvtDateTime, rptEvtObjType, rptEvtParaLen, rptEvtPara}
    STATUS current
    DESCRIPTION
    "Trap of PerEvt: ODU25 TCM1 Incoming Alignment Errored Second."
    ::= { optixTrapsPER 16271 }

--  1.3.6.1.4.1.2011.2.25.3.40.40.30.16272
    perEvtOdu25Tcm2Iaes NOTIFICATION-TYPE
    OBJECTS { rptEvtPeriod, rptEvtValue, rptEvtVldty, rptEvtDateTime, rptEvtObjType, rptEvtParaLen, rptEvtPara}
    STATUS current
    DESCRIPTION
    "Trap of PerEvt: ODU25 TCM2 Incoming Alignment Errored Second."
    ::= { optixTrapsPER 16272 }

--  1.3.6.1.4.1.2011.2.25.3.40.40.30.16273
    perEvtOdu25Tcm3Iaes NOTIFICATION-TYPE
    OBJECTS { rptEvtPeriod, rptEvtValue, rptEvtVldty, rptEvtDateTime, rptEvtObjType, rptEvtParaLen, rptEvtPara}
    STATUS current
    DESCRIPTION
    "Trap of PerEvt: ODU25 TCM3 Incoming Alignment Errored Second."
    ::= { optixTrapsPER 16273 }

--  1.3.6.1.4.1.2011.2.25.3.40.40.30.16274
    perEvtOdu25Tcm4Iaes NOTIFICATION-TYPE
    OBJECTS { rptEvtPeriod, rptEvtValue, rptEvtVldty, rptEvtDateTime, rptEvtObjType, rptEvtParaLen, rptEvtPara}
    STATUS current
    DESCRIPTION
    "Trap of PerEvt: ODU25 TCM4 Incoming Alignment Errored Second."
    ::= { optixTrapsPER 16274 }

--  1.3.6.1.4.1.2011.2.25.3.40.40.30.16275
    perEvtOdu25Tcm5Iaes NOTIFICATION-TYPE
    OBJECTS { rptEvtPeriod, rptEvtValue, rptEvtVldty, rptEvtDateTime, rptEvtObjType, rptEvtParaLen, rptEvtPara}
    STATUS current
    DESCRIPTION
    "Trap of PerEvt: ODU25 TCM5 Incoming Alignment Errored Second."
    ::= { optixTrapsPER 16275 }

--  1.3.6.1.4.1.2011.2.25.3.40.40.30.16276
    perEvtOdu25Tcm6Iaes NOTIFICATION-TYPE
    OBJECTS { rptEvtPeriod, rptEvtValue, rptEvtVldty, rptEvtDateTime, rptEvtObjType, rptEvtParaLen, rptEvtPara}
    STATUS current
    DESCRIPTION
    "Trap of PerEvt: ODU25 TCM5 Incoming Alignment Errored Second."
    ::= { optixTrapsPER 16276 }

--  1.3.6.1.4.1.2011.2.25.3.40.40.30.16277
    perEvtOdu25Tcm1Biaes NOTIFICATION-TYPE
    OBJECTS { rptEvtPeriod, rptEvtValue, rptEvtVldty, rptEvtDateTime, rptEvtObjType, rptEvtParaLen, rptEvtPara}
    STATUS current
    DESCRIPTION
    "Trap of PerEvt: ODU25 TCM1 Backward Incoming Alignment Errored Second."
    ::= { optixTrapsPER 16277 }

--  1.3.6.1.4.1.2011.2.25.3.40.40.30.16278
    perEvtOdu25Tcm2Biaes NOTIFICATION-TYPE
    OBJECTS { rptEvtPeriod, rptEvtValue, rptEvtVldty, rptEvtDateTime, rptEvtObjType, rptEvtParaLen, rptEvtPara}
    STATUS current
    DESCRIPTION
    "Trap of PerEvt: ODU25 TCM2 Backward Incoming Alignment Errored Second."
    ::= { optixTrapsPER 16278 }

--  1.3.6.1.4.1.2011.2.25.3.40.40.30.16279
    perEvtOdu25Tcm3Biaes NOTIFICATION-TYPE
    OBJECTS { rptEvtPeriod, rptEvtValue, rptEvtVldty, rptEvtDateTime, rptEvtObjType, rptEvtParaLen, rptEvtPara}
    STATUS current
    DESCRIPTION
    "Trap of PerEvt: ODU25 TCM3 Backward Incoming Alignment Errored Second."
    ::= { optixTrapsPER 16279 }

--  1.3.6.1.4.1.2011.2.25.3.40.40.30.16280
    perEvtOdu25Tcm4Biaes NOTIFICATION-TYPE
    OBJECTS { rptEvtPeriod, rptEvtValue, rptEvtVldty, rptEvtDateTime, rptEvtObjType, rptEvtParaLen, rptEvtPara}
    STATUS current
    DESCRIPTION
    "Trap of PerEvt: ODU25 TCM4 Backward Incoming Alignment Errored Second."
    ::= { optixTrapsPER 16280 }

--  1.3.6.1.4.1.2011.2.25.3.40.40.30.16281
    perEvtOdu25Tcm5Biaes NOTIFICATION-TYPE
    OBJECTS { rptEvtPeriod, rptEvtValue, rptEvtVldty, rptEvtDateTime, rptEvtObjType, rptEvtParaLen, rptEvtPara}
    STATUS current
    DESCRIPTION
    "Trap of PerEvt: ODU25 TCM5 Backward Incoming Alignment Errored Second."
    ::= { optixTrapsPER 16281 }

--  1.3.6.1.4.1.2011.2.25.3.40.40.30.16282
    perEvtOdu25Tcm6Biaes NOTIFICATION-TYPE
    OBJECTS { rptEvtPeriod, rptEvtValue, rptEvtVldty, rptEvtDateTime, rptEvtObjType, rptEvtParaLen, rptEvtPara}
    STATUS current
    DESCRIPTION
    "Trap of PerEvt: ODU25 TCM6 Backward Incoming Alignment Errored Second."
    ::= { optixTrapsPER 16282 }

--  1.3.6.1.4.1.2011.2.25.3.40.40.30.16283
    perEvtOdu25Tcm1Bbe NOTIFICATION-TYPE
    OBJECTS { rptEvtPeriod, rptEvtValue, rptEvtVldty, rptEvtDateTime, rptEvtObjType, rptEvtParaLen, rptEvtPara}
    STATUS current
    DESCRIPTION
    "Trap of PerEvt: ODU25 TCM1 Background Block Error."
    ::= { optixTrapsPER 16283 }

--  1.3.6.1.4.1.2011.2.25.3.40.40.30.16284
    perEvtOdu25Tcm2Bbe NOTIFICATION-TYPE
    OBJECTS { rptEvtPeriod, rptEvtValue, rptEvtVldty, rptEvtDateTime, rptEvtObjType, rptEvtParaLen, rptEvtPara}
    STATUS current
    DESCRIPTION
    "Trap of PerEvt: ODU25 TCM2 Background Block Error."
    ::= { optixTrapsPER 16284 }

--  1.3.6.1.4.1.2011.2.25.3.40.40.30.16285
    perEvtOdu25Tcm3Bbe NOTIFICATION-TYPE
    OBJECTS { rptEvtPeriod, rptEvtValue, rptEvtVldty, rptEvtDateTime, rptEvtObjType, rptEvtParaLen, rptEvtPara}
    STATUS current
    DESCRIPTION
    "Trap of PerEvt: ODU25 TCM3 Background Block Error."
    ::= { optixTrapsPER 16285 }

--  1.3.6.1.4.1.2011.2.25.3.40.40.30.16286
    perEvtOdu25Tcm4Bbe NOTIFICATION-TYPE
    OBJECTS { rptEvtPeriod, rptEvtValue, rptEvtVldty, rptEvtDateTime, rptEvtObjType, rptEvtParaLen, rptEvtPara}
    STATUS current
    DESCRIPTION
    "Trap of PerEvt: ODU25 TCM4 Background Block Error."
    ::= { optixTrapsPER 16286 }

--  1.3.6.1.4.1.2011.2.25.3.40.40.30.16287
    perEvtOdu25Tcm5Bbe NOTIFICATION-TYPE
    OBJECTS { rptEvtPeriod, rptEvtValue, rptEvtVldty, rptEvtDateTime, rptEvtObjType, rptEvtParaLen, rptEvtPara}
    STATUS current
    DESCRIPTION
    "Trap of PerEvt: ODU25 TCM5 Background Block Error."
    ::= { optixTrapsPER 16287 }

--  1.3.6.1.4.1.2011.2.25.3.40.40.30.16288
    perEvtOdu25Tcm6Bbe NOTIFICATION-TYPE
    OBJECTS { rptEvtPeriod, rptEvtValue, rptEvtVldty, rptEvtDateTime, rptEvtObjType, rptEvtParaLen, rptEvtPara}
    STATUS current
    DESCRIPTION
    "Trap of PerEvt: ODU25 TCM6 Background Block Error."
    ::= { optixTrapsPER 16288 }

--  1.3.6.1.4.1.2011.2.25.3.40.40.30.16289
    perEvtOdu25Tcm1Es NOTIFICATION-TYPE
    OBJECTS { rptEvtPeriod, rptEvtValue, rptEvtVldty, rptEvtDateTime, rptEvtObjType, rptEvtParaLen, rptEvtPara}
    STATUS current
    DESCRIPTION
    "Trap of PerEvt: ODU25 TCM1 Errored Second."
    ::= { optixTrapsPER 16289 }

--  1.3.6.1.4.1.2011.2.25.3.40.40.30.16290
    perEvtOdu25Tcm2Es NOTIFICATION-TYPE
    OBJECTS { rptEvtPeriod, rptEvtValue, rptEvtVldty, rptEvtDateTime, rptEvtObjType, rptEvtParaLen, rptEvtPara}
    STATUS current
    DESCRIPTION
    "Trap of PerEvt: ODU25 TCM2 Errored Second."
    ::= { optixTrapsPER 16290 }

--  1.3.6.1.4.1.2011.2.25.3.40.40.30.16291
    perEvtOdu25Tcm3Es NOTIFICATION-TYPE
    OBJECTS { rptEvtPeriod, rptEvtValue, rptEvtVldty, rptEvtDateTime, rptEvtObjType, rptEvtParaLen, rptEvtPara}
    STATUS current
    DESCRIPTION
    "Trap of PerEvt: ODU25 TCM3 Errored Second."
    ::= { optixTrapsPER 16291 }

--  1.3.6.1.4.1.2011.2.25.3.40.40.30.16292
    perEvtOdu25Tcm4Es NOTIFICATION-TYPE
    OBJECTS { rptEvtPeriod, rptEvtValue, rptEvtVldty, rptEvtDateTime, rptEvtObjType, rptEvtParaLen, rptEvtPara}
    STATUS current
    DESCRIPTION
    "Trap of PerEvt: ODU25 TCM4 Errored Second."
    ::= { optixTrapsPER 16292 }

--  1.3.6.1.4.1.2011.2.25.3.40.40.30.16293
    perEvtOdu25Tcm5Es NOTIFICATION-TYPE
    OBJECTS { rptEvtPeriod, rptEvtValue, rptEvtVldty, rptEvtDateTime, rptEvtObjType, rptEvtParaLen, rptEvtPara}
    STATUS current
    DESCRIPTION
    "Trap of PerEvt: ODU25 TCM5 Errored Second."
    ::= { optixTrapsPER 16293 }

--  1.3.6.1.4.1.2011.2.25.3.40.40.30.16294
    perEvtOdu25Tcm6Es NOTIFICATION-TYPE
    OBJECTS { rptEvtPeriod, rptEvtValue, rptEvtVldty, rptEvtDateTime, rptEvtObjType, rptEvtParaLen, rptEvtPara}
    STATUS current
    DESCRIPTION
    "Trap of PerEvt: ODU25 TCM6 Errored Second."
    ::= { optixTrapsPER 16294 }

--  1.3.6.1.4.1.2011.2.25.3.40.40.30.16295
    perEvtOdu25Tcm1Ses NOTIFICATION-TYPE
    OBJECTS { rptEvtPeriod, rptEvtValue, rptEvtVldty, rptEvtDateTime, rptEvtObjType, rptEvtParaLen, rptEvtPara}
    STATUS current
    DESCRIPTION
    "Trap of PerEvt: ODU25 TCM1 Severely Errored Second."
    ::= { optixTrapsPER 16295 }

--  1.3.6.1.4.1.2011.2.25.3.40.40.30.16296
    perEvtOdu25Tcm2Ses NOTIFICATION-TYPE
    OBJECTS { rptEvtPeriod, rptEvtValue, rptEvtVldty, rptEvtDateTime, rptEvtObjType, rptEvtParaLen, rptEvtPara}
    STATUS current
    DESCRIPTION
    "Trap of PerEvt: ODU25 TCM2 Severely Errored Second."
    ::= { optixTrapsPER 16296 }

--  1.3.6.1.4.1.2011.2.25.3.40.40.30.16297
    perEvtOdu25Tcm3Ses NOTIFICATION-TYPE
    OBJECTS { rptEvtPeriod, rptEvtValue, rptEvtVldty, rptEvtDateTime, rptEvtObjType, rptEvtParaLen, rptEvtPara}
    STATUS current
    DESCRIPTION
    "Trap of PerEvt: ODU25 TCM3 Severely Errored Second."
    ::= { optixTrapsPER 16297 }

--  1.3.6.1.4.1.2011.2.25.3.40.40.30.16298
    perEvtOdu25Tcm4Ses NOTIFICATION-TYPE
    OBJECTS { rptEvtPeriod, rptEvtValue, rptEvtVldty, rptEvtDateTime, rptEvtObjType, rptEvtParaLen, rptEvtPara}
    STATUS current
    DESCRIPTION
    "Trap of PerEvt: ODU25 TCM4 Severely Errored Second."
    ::= { optixTrapsPER 16298 }

--  1.3.6.1.4.1.2011.2.25.3.40.40.30.16299
    perEvtOdu25Tcm5Ses NOTIFICATION-TYPE
    OBJECTS { rptEvtPeriod, rptEvtValue, rptEvtVldty, rptEvtDateTime, rptEvtObjType, rptEvtParaLen, rptEvtPara}
    STATUS current
    DESCRIPTION
    "Trap of PerEvt: ODU25 TCM5 Severely Errored Second."
    ::= { optixTrapsPER 16299 }

--  1.3.6.1.4.1.2011.2.25.3.40.40.30.16300
    perEvtOdu25Tcm6Ses NOTIFICATION-TYPE
    OBJECTS { rptEvtPeriod, rptEvtValue, rptEvtVldty, rptEvtDateTime, rptEvtObjType, rptEvtParaLen, rptEvtPara}
    STATUS current
    DESCRIPTION
    "Trap of PerEvt: ODU25 TCM6 Severely Errored Second."
    ::= { optixTrapsPER 16300 }

--  1.3.6.1.4.1.2011.2.25.3.40.40.30.16301
    perEvtOdu25Tcm1Uas NOTIFICATION-TYPE
    OBJECTS { rptEvtPeriod, rptEvtValue, rptEvtVldty, rptEvtDateTime, rptEvtObjType, rptEvtParaLen, rptEvtPara}
    STATUS current
    DESCRIPTION
    "Trap of PerEvt: ODU25 TCM1 Unavailable Seconds."
    ::= { optixTrapsPER 16301 }

--  1.3.6.1.4.1.2011.2.25.3.40.40.30.16302
    perEvtOdu25Tcm2Uas NOTIFICATION-TYPE
    OBJECTS { rptEvtPeriod, rptEvtValue, rptEvtVldty, rptEvtDateTime, rptEvtObjType, rptEvtParaLen, rptEvtPara}
    STATUS current
    DESCRIPTION
    "Trap of PerEvt: ODU25 TCM2 Unavailable Seconds."
    ::= { optixTrapsPER 16302 }

--  1.3.6.1.4.1.2011.2.25.3.40.40.30.16303
    perEvtOdu25Tcm3Uas NOTIFICATION-TYPE
    OBJECTS { rptEvtPeriod, rptEvtValue, rptEvtVldty, rptEvtDateTime, rptEvtObjType, rptEvtParaLen, rptEvtPara}
    STATUS current
    DESCRIPTION
    "Trap of PerEvt: ODU25 TCM3 Unavailable Seconds."
    ::= { optixTrapsPER 16303 }

--  1.3.6.1.4.1.2011.2.25.3.40.40.30.16304
    perEvtOdu25Tcm4Uas NOTIFICATION-TYPE
    OBJECTS { rptEvtPeriod, rptEvtValue, rptEvtVldty, rptEvtDateTime, rptEvtObjType, rptEvtParaLen, rptEvtPara}
    STATUS current
    DESCRIPTION
    "Trap of PerEvt: ODU25 TCM4 Unavailable Seconds."
    ::= { optixTrapsPER 16304 }

--  1.3.6.1.4.1.2011.2.25.3.40.40.30.16305
    perEvtOdu25Tcm5Uas NOTIFICATION-TYPE
    OBJECTS { rptEvtPeriod, rptEvtValue, rptEvtVldty, rptEvtDateTime, rptEvtObjType, rptEvtParaLen, rptEvtPara}
    STATUS current
    DESCRIPTION
    "Trap of PerEvt: ODU25 TCM5 Unavailable Seconds."
    ::= { optixTrapsPER 16305 }

--  1.3.6.1.4.1.2011.2.25.3.40.40.30.16306
    perEvtOdu25Tcm6Uas NOTIFICATION-TYPE
    OBJECTS { rptEvtPeriod, rptEvtValue, rptEvtVldty, rptEvtDateTime, rptEvtObjType, rptEvtParaLen, rptEvtPara}
    STATUS current
    DESCRIPTION
    "Trap of PerEvt: ODU25 TCM6 Unavailable Seconds."
    ::= { optixTrapsPER 16306 }

--  1.3.6.1.4.1.2011.2.25.3.40.40.30.16307
    perEvtOdu25Tcm1Sesr NOTIFICATION-TYPE
    OBJECTS { rptEvtPeriod, rptEvtValue, rptEvtVldty, rptEvtDateTime, rptEvtObjType, rptEvtParaLen, rptEvtPara}
    STATUS current
    DESCRIPTION
    "Trap of PerEvt: ODU25 TCM1 Severely Errored Second Ratio."
    ::= { optixTrapsPER 16307 }

--  1.3.6.1.4.1.2011.2.25.3.40.40.30.16308
    perEvtOdu25Tcm2Sesr NOTIFICATION-TYPE
    OBJECTS { rptEvtPeriod, rptEvtValue, rptEvtVldty, rptEvtDateTime, rptEvtObjType, rptEvtParaLen, rptEvtPara}
    STATUS current
    DESCRIPTION
    "Trap of PerEvt: ODU25 TCM2 Severely Errored Second Ratio."
    ::= { optixTrapsPER 16308 }

--  1.3.6.1.4.1.2011.2.25.3.40.40.30.16309
    perEvtOdu25Tcm3Sesr NOTIFICATION-TYPE
    OBJECTS { rptEvtPeriod, rptEvtValue, rptEvtVldty, rptEvtDateTime, rptEvtObjType, rptEvtParaLen, rptEvtPara}
    STATUS current
    DESCRIPTION
    "Trap of PerEvt: ODU25 TCM3 Severely Errored Second Ratio."
    ::= { optixTrapsPER 16309 }

--  1.3.6.1.4.1.2011.2.25.3.40.40.30.16310
    perEvtOdu25Tcm4Sesr NOTIFICATION-TYPE
    OBJECTS { rptEvtPeriod, rptEvtValue, rptEvtVldty, rptEvtDateTime, rptEvtObjType, rptEvtParaLen, rptEvtPara}
    STATUS current
    DESCRIPTION
    "Trap of PerEvt: ODU25 TCM4 Severely Errored Second Ratio."
    ::= { optixTrapsPER 16310 }

--  1.3.6.1.4.1.2011.2.25.3.40.40.30.16311
    perEvtOdu25Tcm5Sesr NOTIFICATION-TYPE
    OBJECTS { rptEvtPeriod, rptEvtValue, rptEvtVldty, rptEvtDateTime, rptEvtObjType, rptEvtParaLen, rptEvtPara}
    STATUS current
    DESCRIPTION
    "Trap of PerEvt: ODU25 TCM5 Severely Errored Second Ratio."
    ::= { optixTrapsPER 16311 }

--  1.3.6.1.4.1.2011.2.25.3.40.40.30.16312
    perEvtOdu25Tcm6Sesr NOTIFICATION-TYPE
    OBJECTS { rptEvtPeriod, rptEvtValue, rptEvtVldty, rptEvtDateTime, rptEvtObjType, rptEvtParaLen, rptEvtPara}
    STATUS current
    DESCRIPTION
    "Trap of PerEvt: ODU25 TCM6 Severely Errored Second Ratio."
    ::= { optixTrapsPER 16312 }

--  1.3.6.1.4.1.2011.2.25.3.40.40.30.16313
    perEvtOdu25Tcm1Bber NOTIFICATION-TYPE
    OBJECTS { rptEvtPeriod, rptEvtValue, rptEvtVldty, rptEvtDateTime, rptEvtObjType, rptEvtParaLen, rptEvtPara}
    STATUS current
    DESCRIPTION
    "Trap of PerEvt: ODU25 TCM1 Background Block Error Ratio."
    ::= { optixTrapsPER 16313 }

--  1.3.6.1.4.1.2011.2.25.3.40.40.30.16314
    perEvtOdu25Tcm2Bber NOTIFICATION-TYPE
    OBJECTS { rptEvtPeriod, rptEvtValue, rptEvtVldty, rptEvtDateTime, rptEvtObjType, rptEvtParaLen, rptEvtPara}
    STATUS current
    DESCRIPTION
    "Trap of PerEvt: ODU25 TCM2 Background Block Error Ratio."
    ::= { optixTrapsPER 16314 }

--  1.3.6.1.4.1.2011.2.25.3.40.40.30.16315
    perEvtOdu25Tcm3Bber NOTIFICATION-TYPE
    OBJECTS { rptEvtPeriod, rptEvtValue, rptEvtVldty, rptEvtDateTime, rptEvtObjType, rptEvtParaLen, rptEvtPara}
    STATUS current
    DESCRIPTION
    "Trap of PerEvt: ODU25 TCM3 Background Block Error Ratio."
    ::= { optixTrapsPER 16315 }

--  1.3.6.1.4.1.2011.2.25.3.40.40.30.16316
    perEvtOdu25Tcm4Bber NOTIFICATION-TYPE
    OBJECTS { rptEvtPeriod, rptEvtValue, rptEvtVldty, rptEvtDateTime, rptEvtObjType, rptEvtParaLen, rptEvtPara}
    STATUS current
    DESCRIPTION
    "Trap of PerEvt: ODU25 TCM4 Background Block Error Ratio."
    ::= { optixTrapsPER 16316 }

--  1.3.6.1.4.1.2011.2.25.3.40.40.30.16317
    perEvtOdu25Tcm5Bber NOTIFICATION-TYPE
    OBJECTS { rptEvtPeriod, rptEvtValue, rptEvtVldty, rptEvtDateTime, rptEvtObjType, rptEvtParaLen, rptEvtPara}
    STATUS current
    DESCRIPTION
    "Trap of PerEvt: ODU25 TCM5 Background Block Error Ratio."
    ::= { optixTrapsPER 16317 }

--  1.3.6.1.4.1.2011.2.25.3.40.40.30.16318
    perEvtOdu25Tcm6Bber NOTIFICATION-TYPE
    OBJECTS { rptEvtPeriod, rptEvtValue, rptEvtVldty, rptEvtDateTime, rptEvtObjType, rptEvtParaLen, rptEvtPara}
    STATUS current
    DESCRIPTION
    "Trap of PerEvt: ODU25 TCM6 Background Block Error Ratio."
    ::= { optixTrapsPER 16318 }

--  1.3.6.1.4.1.2011.2.25.3.40.40.30.16319
    perEvtOdu25Tcm1Febbe NOTIFICATION-TYPE
    OBJECTS { rptEvtPeriod, rptEvtValue, rptEvtVldty, rptEvtDateTime, rptEvtObjType, rptEvtParaLen, rptEvtPara}
    STATUS current
    DESCRIPTION
    "Trap of PerEvt: ODU25 TCM1 Far Background Block Error."
    ::= { optixTrapsPER 16319 }

--  1.3.6.1.4.1.2011.2.25.3.40.40.30.16320
    perEvtOdu25Tcm2Febbe NOTIFICATION-TYPE
    OBJECTS { rptEvtPeriod, rptEvtValue, rptEvtVldty, rptEvtDateTime, rptEvtObjType, rptEvtParaLen, rptEvtPara}
    STATUS current
    DESCRIPTION
    "Trap of PerEvt: ODU25 TCM2 Far Background Block Error."
    ::= { optixTrapsPER 16320 }

--  1.3.6.1.4.1.2011.2.25.3.40.40.30.16321
    perEvtOdu25Tcm3Febbe NOTIFICATION-TYPE
    OBJECTS { rptEvtPeriod, rptEvtValue, rptEvtVldty, rptEvtDateTime, rptEvtObjType, rptEvtParaLen, rptEvtPara}
    STATUS current
    DESCRIPTION
    "Trap of PerEvt: ODU25 TCM3 Far Background Block Error."
    ::= { optixTrapsPER 16321 }

--  1.3.6.1.4.1.2011.2.25.3.40.40.30.16322
    perEvtOdu25Tcm4Febbe NOTIFICATION-TYPE
    OBJECTS { rptEvtPeriod, rptEvtValue, rptEvtVldty, rptEvtDateTime, rptEvtObjType, rptEvtParaLen, rptEvtPara}
    STATUS current
    DESCRIPTION
    "Trap of PerEvt: ODU25 TCM4 Far Background Block Error."
    ::= { optixTrapsPER 16322 }

--  1.3.6.1.4.1.2011.2.25.3.40.40.30.16323
    perEvtOdu25Tcm5Febbe NOTIFICATION-TYPE
    OBJECTS { rptEvtPeriod, rptEvtValue, rptEvtVldty, rptEvtDateTime, rptEvtObjType, rptEvtParaLen, rptEvtPara}
    STATUS current
    DESCRIPTION
    "Trap of PerEvt: ODU25 TCM5 Far Background Block Error."
    ::= { optixTrapsPER 16323 }

--  1.3.6.1.4.1.2011.2.25.3.40.40.30.16324
    perEvtOdu25Tcm6Febbe NOTIFICATION-TYPE
    OBJECTS { rptEvtPeriod, rptEvtValue, rptEvtVldty, rptEvtDateTime, rptEvtObjType, rptEvtParaLen, rptEvtPara}
    STATUS current
    DESCRIPTION
    "Trap of PerEvt: ODU25 TCM6 Far Background Block Error."
    ::= { optixTrapsPER 16324 }

--  1.3.6.1.4.1.2011.2.25.3.40.40.30.16325
    perEvtOdu25Tcm1Fees NOTIFICATION-TYPE
    OBJECTS { rptEvtPeriod, rptEvtValue, rptEvtVldty, rptEvtDateTime, rptEvtObjType, rptEvtParaLen, rptEvtPara}
    STATUS current
    DESCRIPTION
    "Trap of PerEvt: ODU25 TCM1 Far Errored Second."
    ::= { optixTrapsPER 16325 }

--  1.3.6.1.4.1.2011.2.25.3.40.40.30.16326
    perEvtOdu25Tcm2Fees NOTIFICATION-TYPE
    OBJECTS { rptEvtPeriod, rptEvtValue, rptEvtVldty, rptEvtDateTime, rptEvtObjType, rptEvtParaLen, rptEvtPara}
    STATUS current
    DESCRIPTION
    "Trap of PerEvt: ODU25 TCM2 Far Errored Second."
    ::= { optixTrapsPER 16326 }

--  1.3.6.1.4.1.2011.2.25.3.40.40.30.16327
    perEvtOdu25Tcm3Fees NOTIFICATION-TYPE
    OBJECTS { rptEvtPeriod, rptEvtValue, rptEvtVldty, rptEvtDateTime, rptEvtObjType, rptEvtParaLen, rptEvtPara}
    STATUS current
    DESCRIPTION
    "Trap of PerEvt: ODU25 TCM3 Far Errored Second."
    ::= { optixTrapsPER 16327 }

--  1.3.6.1.4.1.2011.2.25.3.40.40.30.16328
    perEvtOdu25Tcm4Fees NOTIFICATION-TYPE
    OBJECTS { rptEvtPeriod, rptEvtValue, rptEvtVldty, rptEvtDateTime, rptEvtObjType, rptEvtParaLen, rptEvtPara}
    STATUS current
    DESCRIPTION
    "Trap of PerEvt: ODU25 TCM4 Far Errored Second."
    ::= { optixTrapsPER 16328 }

--  1.3.6.1.4.1.2011.2.25.3.40.40.30.16329
    perEvtOdu25Tcm5Fees NOTIFICATION-TYPE
    OBJECTS { rptEvtPeriod, rptEvtValue, rptEvtVldty, rptEvtDateTime, rptEvtObjType, rptEvtParaLen, rptEvtPara}
    STATUS current
    DESCRIPTION
    "Trap of PerEvt: ODU25 TCM5 Far Errored Second."
    ::= { optixTrapsPER 16329 }

--  1.3.6.1.4.1.2011.2.25.3.40.40.30.16330
    perEvtOdu25Tcm6Fees NOTIFICATION-TYPE
    OBJECTS { rptEvtPeriod, rptEvtValue, rptEvtVldty, rptEvtDateTime, rptEvtObjType, rptEvtParaLen, rptEvtPara}
    STATUS current
    DESCRIPTION
    "Trap of PerEvt: ODU25 TCM6 Far Errored Second."
    ::= { optixTrapsPER 16330 }

--  1.3.6.1.4.1.2011.2.25.3.40.40.30.16331
    perEvtOdu25Tcm1Feses NOTIFICATION-TYPE
    OBJECTS { rptEvtPeriod, rptEvtValue, rptEvtVldty, rptEvtDateTime, rptEvtObjType, rptEvtParaLen, rptEvtPara}
    STATUS current
    DESCRIPTION
    "Trap of PerEvt: ODU25 TCM1 Far Severely Errored Second."
    ::= { optixTrapsPER 16331 }

--  1.3.6.1.4.1.2011.2.25.3.40.40.30.16332
    perEvtOdu25Tcm2Feses NOTIFICATION-TYPE
    OBJECTS { rptEvtPeriod, rptEvtValue, rptEvtVldty, rptEvtDateTime, rptEvtObjType, rptEvtParaLen, rptEvtPara}
    STATUS current
    DESCRIPTION
    "Trap of PerEvt: ODU25 TCM2 Far Severely Errored Second."
    ::= { optixTrapsPER 16332 }

--  1.3.6.1.4.1.2011.2.25.3.40.40.30.16333
    perEvtOdu25Tcm3Feses NOTIFICATION-TYPE
    OBJECTS { rptEvtPeriod, rptEvtValue, rptEvtVldty, rptEvtDateTime, rptEvtObjType, rptEvtParaLen, rptEvtPara}
    STATUS current
    DESCRIPTION
    "Trap of PerEvt: ODU25 TCM3 Far Severely Errored Second."
    ::= { optixTrapsPER 16333 }

--  1.3.6.1.4.1.2011.2.25.3.40.40.30.16334
    perEvtOdu25Tcm4Feses NOTIFICATION-TYPE
    OBJECTS { rptEvtPeriod, rptEvtValue, rptEvtVldty, rptEvtDateTime, rptEvtObjType, rptEvtParaLen, rptEvtPara}
    STATUS current
    DESCRIPTION
    "Trap of PerEvt: ODU25 TCM4 Far Severely Errored Second."
    ::= { optixTrapsPER 16334 }

--  1.3.6.1.4.1.2011.2.25.3.40.40.30.16335
    perEvtOdu25Tcm5Feses NOTIFICATION-TYPE
    OBJECTS { rptEvtPeriod, rptEvtValue, rptEvtVldty, rptEvtDateTime, rptEvtObjType, rptEvtParaLen, rptEvtPara}
    STATUS current
    DESCRIPTION
    "Trap of PerEvt: ODU25 TCM5 Far Severely Errored Second."
    ::= { optixTrapsPER 16335 }

--  1.3.6.1.4.1.2011.2.25.3.40.40.30.16336
    perEvtOdu25Tcm6Feses NOTIFICATION-TYPE
    OBJECTS { rptEvtPeriod, rptEvtValue, rptEvtVldty, rptEvtDateTime, rptEvtObjType, rptEvtParaLen, rptEvtPara}
    STATUS current
    DESCRIPTION
    "Trap of PerEvt: ODU25 TCM6 Far Severely Errored Second."
    ::= { optixTrapsPER 16336 }

--  1.3.6.1.4.1.2011.2.25.3.40.40.30.16337
    perEvtOdu25Tcm1Feuas NOTIFICATION-TYPE
    OBJECTS { rptEvtPeriod, rptEvtValue, rptEvtVldty, rptEvtDateTime, rptEvtObjType, rptEvtParaLen, rptEvtPara}
    STATUS current
    DESCRIPTION
    "Trap of PerEvt: ODU25 TCM1 Far Unavailable Seconds."
    ::= { optixTrapsPER 16337 }

--  1.3.6.1.4.1.2011.2.25.3.40.40.30.16338
    perEvtOdu25Tcm2Feuas NOTIFICATION-TYPE
    OBJECTS { rptEvtPeriod, rptEvtValue, rptEvtVldty, rptEvtDateTime, rptEvtObjType, rptEvtParaLen, rptEvtPara}
    STATUS current
    DESCRIPTION
    "Trap of PerEvt: ODU25 TCM2 Far Unavailable Seconds."
    ::= { optixTrapsPER 16338 }

--  1.3.6.1.4.1.2011.2.25.3.40.40.30.16339
    perEvtOdu25Tcm3Feuas NOTIFICATION-TYPE
    OBJECTS { rptEvtPeriod, rptEvtValue, rptEvtVldty, rptEvtDateTime, rptEvtObjType, rptEvtParaLen, rptEvtPara}
    STATUS current
    DESCRIPTION
    "Trap of PerEvt: ODU25 TCM3 Far Unavailable Seconds."
    ::= { optixTrapsPER 16339 }

--  1.3.6.1.4.1.2011.2.25.3.40.40.30.16340
    perEvtOdu25Tcm4Feuas NOTIFICATION-TYPE
    OBJECTS { rptEvtPeriod, rptEvtValue, rptEvtVldty, rptEvtDateTime, rptEvtObjType, rptEvtParaLen, rptEvtPara}
    STATUS current
    DESCRIPTION
    "Trap of PerEvt: ODU25 TCM4 Far Unavailable Seconds."
    ::= { optixTrapsPER 16340 }

--  1.3.6.1.4.1.2011.2.25.3.40.40.30.16341
    perEvtOdu25Tcm5Feuas NOTIFICATION-TYPE
    OBJECTS { rptEvtPeriod, rptEvtValue, rptEvtVldty, rptEvtDateTime, rptEvtObjType, rptEvtParaLen, rptEvtPara}
    STATUS current
    DESCRIPTION
    "Trap of PerEvt: ODU25 TCM5 Far Unavailable Seconds."
    ::= { optixTrapsPER 16341 }

--  1.3.6.1.4.1.2011.2.25.3.40.40.30.16342
    perEvtOdu25Tcm6Feuas NOTIFICATION-TYPE
    OBJECTS { rptEvtPeriod, rptEvtValue, rptEvtVldty, rptEvtDateTime, rptEvtObjType, rptEvtParaLen, rptEvtPara}
    STATUS current
    DESCRIPTION
    "Trap of PerEvt: ODU25 TCM6 Far Unavailable Seconds."
    ::= { optixTrapsPER 16342 }

--  1.3.6.1.4.1.2011.2.25.3.40.40.30.16343
    perEvtOdu25Tcm1Fesesr NOTIFICATION-TYPE
    OBJECTS { rptEvtPeriod, rptEvtValue, rptEvtVldty, rptEvtDateTime, rptEvtObjType, rptEvtParaLen, rptEvtPara}
    STATUS current
    DESCRIPTION
    "Trap of PerEvt: ODU25 TCM1 Far Severely Errored Second Ratio."
    ::= { optixTrapsPER 16343 }

--  1.3.6.1.4.1.2011.2.25.3.40.40.30.16344
    perEvtOdu25Tcm2Fesesr NOTIFICATION-TYPE
    OBJECTS { rptEvtPeriod, rptEvtValue, rptEvtVldty, rptEvtDateTime, rptEvtObjType, rptEvtParaLen, rptEvtPara}
    STATUS current
    DESCRIPTION
    "Trap of PerEvt: ODU25 TCM2 Far Severely Errored Second Ratio."
    ::= { optixTrapsPER 16344 }

--  1.3.6.1.4.1.2011.2.25.3.40.40.30.16345
    perEvtOdu25Tcm3Fesesr NOTIFICATION-TYPE
    OBJECTS { rptEvtPeriod, rptEvtValue, rptEvtVldty, rptEvtDateTime, rptEvtObjType, rptEvtParaLen, rptEvtPara}
    STATUS current
    DESCRIPTION
    "Trap of PerEvt: ODU25 TCM3 Far Severely Errored Second Ratio."
    ::= { optixTrapsPER 16345 }

--  1.3.6.1.4.1.2011.2.25.3.40.40.30.16346
    perEvtOdu25Tcm4Fesesr NOTIFICATION-TYPE
    OBJECTS { rptEvtPeriod, rptEvtValue, rptEvtVldty, rptEvtDateTime, rptEvtObjType, rptEvtParaLen, rptEvtPara}
    STATUS current
    DESCRIPTION
    "Trap of PerEvt: ODU25 TCM4 Far Severely Errored Second Ratio."
    ::= { optixTrapsPER 16346 }

--  1.3.6.1.4.1.2011.2.25.3.40.40.30.16347
    perEvtOdu25Tcm5Fesesr NOTIFICATION-TYPE
    OBJECTS { rptEvtPeriod, rptEvtValue, rptEvtVldty, rptEvtDateTime, rptEvtObjType, rptEvtParaLen, rptEvtPara}
    STATUS current
    DESCRIPTION
    "Trap of PerEvt: ODU25 TCM5 Far Severely Errored Second Ratio."
    ::= { optixTrapsPER 16347 }

--  1.3.6.1.4.1.2011.2.25.3.40.40.30.16348
    perEvtOdu25Tcm6Fesesr NOTIFICATION-TYPE
    OBJECTS { rptEvtPeriod, rptEvtValue, rptEvtVldty, rptEvtDateTime, rptEvtObjType, rptEvtParaLen, rptEvtPara}
    STATUS current
    DESCRIPTION
    "Trap of PerEvt: ODU25 TCM6 Far Severely Errored Second Ratio."
    ::= { optixTrapsPER 16348 }

--  1.3.6.1.4.1.2011.2.25.3.40.40.30.16349
    perEvtOdu25Tcm1Febber NOTIFICATION-TYPE
    OBJECTS { rptEvtPeriod, rptEvtValue, rptEvtVldty, rptEvtDateTime, rptEvtObjType, rptEvtParaLen, rptEvtPara}
    STATUS current
    DESCRIPTION
    "Trap of PerEvt: ODU25 TCM1 Far Background Block Error Ratio."
    ::= { optixTrapsPER 16349 }

--  1.3.6.1.4.1.2011.2.25.3.40.40.30.16350
    perEvtOdu25Tcm2Febber NOTIFICATION-TYPE
    OBJECTS { rptEvtPeriod, rptEvtValue, rptEvtVldty, rptEvtDateTime, rptEvtObjType, rptEvtParaLen, rptEvtPara}
    STATUS current
    DESCRIPTION
    "Trap of PerEvt: ODU25 TCM2 Far Background Block Error Ratio."
    ::= { optixTrapsPER 16350 }

--  1.3.6.1.4.1.2011.2.25.3.40.40.30.16351
    perEvtOdu25Tcm3Febber NOTIFICATION-TYPE
    OBJECTS { rptEvtPeriod, rptEvtValue, rptEvtVldty, rptEvtDateTime, rptEvtObjType, rptEvtParaLen, rptEvtPara}
    STATUS current
    DESCRIPTION
    "Trap of PerEvt: ODU25 TCM3 Far Background Block Error Ratio."
    ::= { optixTrapsPER 16351 }

--  1.3.6.1.4.1.2011.2.25.3.40.40.30.16352
    perEvtOdu25Tcm4Febber NOTIFICATION-TYPE
    OBJECTS { rptEvtPeriod, rptEvtValue, rptEvtVldty, rptEvtDateTime, rptEvtObjType, rptEvtParaLen, rptEvtPara}
    STATUS current
    DESCRIPTION
    "Trap of PerEvt: ODU25 TCM4 Far Background Block Error Ratio."
    ::= { optixTrapsPER 16352 }

--  1.3.6.1.4.1.2011.2.25.3.40.40.30.16353
    perEvtOdu25Tcm5Febber NOTIFICATION-TYPE
    OBJECTS { rptEvtPeriod, rptEvtValue, rptEvtVldty, rptEvtDateTime, rptEvtObjType, rptEvtParaLen, rptEvtPara}
    STATUS current
    DESCRIPTION
    "Trap of PerEvt: ODU25 TCM5 Far Background Block Error Ratio."
    ::= { optixTrapsPER 16353 }

--  1.3.6.1.4.1.2011.2.25.3.40.40.30.16354
    perEvtOdu25Tcm6Febber NOTIFICATION-TYPE
    OBJECTS { rptEvtPeriod, rptEvtValue, rptEvtVldty, rptEvtDateTime, rptEvtObjType, rptEvtParaLen, rptEvtPara}
    STATUS current
    DESCRIPTION
    "Trap of PerEvt: ODU25 TCM6 Far Background Block Error Ratio."
    ::= { optixTrapsPER 16354 }

--  1.3.6.1.4.1.2011.2.25.3.40.40.30.16355
    perEvtOdu25Tcm1Tmp NOTIFICATION-TYPE
    OBJECTS { rptEvtPeriod, rptEvtValue, rptEvtVldty, rptEvtDateTime, rptEvtObjType, rptEvtParaLen, rptEvtPara}
    STATUS current
    DESCRIPTION
    "Trap of PerEvt: ODU25 TCM1 Section Total Monitor Period."
    ::= { optixTrapsPER 16355 }

--  1.3.6.1.4.1.2011.2.25.3.40.40.30.16356
    perEvtOdu25Tcm2Tmp NOTIFICATION-TYPE
    OBJECTS { rptEvtPeriod, rptEvtValue, rptEvtVldty, rptEvtDateTime, rptEvtObjType, rptEvtParaLen, rptEvtPara}
    STATUS current
    DESCRIPTION
    "Trap of PerEvt: ODU25 TCM2 Section Total Monitor Period."
    ::= { optixTrapsPER 16356 }

--  1.3.6.1.4.1.2011.2.25.3.40.40.30.16357
    perEvtOdu25Tcm3Tmp NOTIFICATION-TYPE
    OBJECTS { rptEvtPeriod, rptEvtValue, rptEvtVldty, rptEvtDateTime, rptEvtObjType, rptEvtParaLen, rptEvtPara}
    STATUS current
    DESCRIPTION
    "Trap of PerEvt: ODU25 TCM3 Section Total Monitor Period."
    ::= { optixTrapsPER 16357 }

--  1.3.6.1.4.1.2011.2.25.3.40.40.30.16358
    perEvtOdu25Tcm4Tmp NOTIFICATION-TYPE
    OBJECTS { rptEvtPeriod, rptEvtValue, rptEvtVldty, rptEvtDateTime, rptEvtObjType, rptEvtParaLen, rptEvtPara}
    STATUS current
    DESCRIPTION
    "Trap of PerEvt: ODU25 TCM4 Section Total Monitor Period."
    ::= { optixTrapsPER 16358 }

--  1.3.6.1.4.1.2011.2.25.3.40.40.30.16359
    perEvtOdu25Tcm5Tmp NOTIFICATION-TYPE
    OBJECTS { rptEvtPeriod, rptEvtValue, rptEvtVldty, rptEvtDateTime, rptEvtObjType, rptEvtParaLen, rptEvtPara}
    STATUS current
    DESCRIPTION
    "Trap of PerEvt: ODU25 TCM5 Section Total Monitor Period."
    ::= { optixTrapsPER 16359 }

--  1.3.6.1.4.1.2011.2.25.3.40.40.30.16360
    perEvtOdu25Tcm6Tmp NOTIFICATION-TYPE
    OBJECTS { rptEvtPeriod, rptEvtValue, rptEvtVldty, rptEvtDateTime, rptEvtObjType, rptEvtParaLen, rptEvtPara}
    STATUS current
    DESCRIPTION
    "Trap of PerEvt: ODU25 TCM6 Section Total Monitor Period."
    ::= { optixTrapsPER 16360 }

--  1.3.6.1.4.1.2011.2.25.3.40.40.30.15011
    perEvtCorrErrBefFecAver15m NOTIFICATION-TYPE
    OBJECTS { rptEvtPeriod, rptEvtValue, rptEvtVldty, rptEvtDateTime, rptEvtObjType, rptEvtParaLen, rptEvtPara}
    STATUS current
    DESCRIPTION
    "Trap of PerEvt: perEvtCorrErrBefFecAver15m."
    ::= { optixTrapsPER 15011 }

--  1.3.6.1.4.1.2011.2.25.3.40.40.30.15012
    perEvtCorrErrAftFecAver15m NOTIFICATION-TYPE
    OBJECTS { rptEvtPeriod, rptEvtValue, rptEvtVldty, rptEvtDateTime, rptEvtObjType, rptEvtParaLen, rptEvtPara}
    STATUS current
    DESCRIPTION
    "Trap of PerEvt: perEvt corrErrAftFecAver15m."
    ::= { optixTrapsPER 15012 }

--  1.3.6.1.4.1.2011.2.25.3.40.40.30.15013
    perEvtCorrErrBefFecAver24h NOTIFICATION-TYPE
    OBJECTS { rptEvtPeriod, rptEvtValue, rptEvtVldty, rptEvtDateTime, rptEvtObjType, rptEvtParaLen, rptEvtPara}
    STATUS current
    DESCRIPTION
    "Trap of PerEvt: perEvtCorrErrBefFecAver24h."
    ::= { optixTrapsPER 15013 }

--  1.3.6.1.4.1.2011.2.25.3.40.40.30.15014
    perEvtCorrErrAftFecAver24h NOTIFICATION-TYPE
    OBJECTS { rptEvtPeriod, rptEvtValue, rptEvtVldty, rptEvtDateTime, rptEvtObjType, rptEvtParaLen, rptEvtPara}
    STATUS current
    DESCRIPTION
    "Trap of PerEvt: perEvtCorrErrAftFecAver24h."
    ::= { optixTrapsPER 15014 }

--  1.3.6.1.4.1.2011.2.25.3.40.40.30.16215
    perEvtOtu0Uas NOTIFICATION-TYPE
    OBJECTS { rptEvtPeriod, rptEvtValue, rptEvtVldty, rptEvtDateTime, rptEvtObjType, rptEvtParaLen, rptEvtPara}
    STATUS current
    DESCRIPTION
    "Trap of PerEvt: OTU0 SM Unavailable Seconds."
    ::= { optixTrapsPER 16215 }

--  1.3.6.1.4.1.2011.2.25.3.40.40.30.16216
    perEvtOtu0Ses NOTIFICATION-TYPE
    OBJECTS { rptEvtPeriod, rptEvtValue, rptEvtVldty, rptEvtDateTime, rptEvtObjType, rptEvtParaLen, rptEvtPara}
    STATUS current
    DESCRIPTION
    "Trap of PerEvt: OTU0 SM Severely Errored Second."
    ::= { optixTrapsPER 16216 }

--  1.3.6.1.4.1.2011.2.25.3.40.40.30.16217
    perEvtOtu0Feses NOTIFICATION-TYPE
    OBJECTS { rptEvtPeriod, rptEvtValue, rptEvtVldty, rptEvtDateTime, rptEvtObjType, rptEvtParaLen, rptEvtPara}
    STATUS current
    DESCRIPTION
    "Trap of PerEvt: OTU0 SM Far Severely Errored Second."
    ::= { optixTrapsPER 16217 }

--  1.3.6.1.4.1.2011.2.25.3.40.40.30.16218
    perEvtOtu0Fees NOTIFICATION-TYPE
    OBJECTS { rptEvtPeriod, rptEvtValue, rptEvtVldty, rptEvtDateTime, rptEvtObjType, rptEvtParaLen, rptEvtPara}
    STATUS current
    DESCRIPTION
    "Trap of PerEvt: OTU0 SM Far Errored Second."
    ::= { optixTrapsPER 16218 }

--  1.3.6.1.4.1.2011.2.25.3.40.40.30.16219
    perEvtOtu0Tmp NOTIFICATION-TYPE
    OBJECTS { rptEvtPeriod, rptEvtValue, rptEvtVldty, rptEvtDateTime, rptEvtObjType, rptEvtParaLen, rptEvtPara}
    STATUS current
    DESCRIPTION
    "Trap of PerEvt: OTU0 Total Monitor Period."
    ::= { optixTrapsPER 16219 }

--  1.3.6.1.4.1.2011.2.25.3.40.40.30.16220
    perEvtOtu0Sesr NOTIFICATION-TYPE
    OBJECTS { rptEvtPeriod, rptEvtValue, rptEvtVldty, rptEvtDateTime, rptEvtObjType, rptEvtParaLen, rptEvtPara}
    STATUS current
    DESCRIPTION
    "Trap of PerEvt: OTU0 SM Severely Errored Second Ratio."
    ::= { optixTrapsPER 16220 }

--  1.3.6.1.4.1.2011.2.25.3.40.40.30.16221
    perEvtOtu0Feuas NOTIFICATION-TYPE
    OBJECTS { rptEvtPeriod, rptEvtValue, rptEvtVldty, rptEvtDateTime, rptEvtObjType, rptEvtParaLen, rptEvtPara}
    STATUS current
    DESCRIPTION
    "Trap of PerEvt: OTU0 SM Far Unavailable Seconds."
    ::= { optixTrapsPER 16221 }

--  1.3.6.1.4.1.2011.2.25.3.40.40.30.16222
    perEvtOtu0Bbe NOTIFICATION-TYPE
    OBJECTS { rptEvtPeriod, rptEvtValue, rptEvtVldty, rptEvtDateTime, rptEvtObjType, rptEvtParaLen, rptEvtPara}
    STATUS current
    DESCRIPTION
    "Trap of PerEvt: OTU0 SM Background Block Error."
    ::= { optixTrapsPER 16222 }

--  1.3.6.1.4.1.2011.2.25.3.40.40.30.16223
    perEvtOtu0Fesesr NOTIFICATION-TYPE
    OBJECTS { rptEvtPeriod, rptEvtValue, rptEvtVldty, rptEvtDateTime, rptEvtObjType, rptEvtParaLen, rptEvtPara}
    STATUS current
    DESCRIPTION
    "Trap of PerEvt: OTU0 SM Far Severely Errored Second Ratio."
    ::= { optixTrapsPER 16223 }

--  1.3.6.1.4.1.2011.2.25.3.40.40.30.16224
    perEvtOtu0Iaes NOTIFICATION-TYPE
    OBJECTS { rptEvtPeriod, rptEvtValue, rptEvtVldty, rptEvtDateTime, rptEvtObjType, rptEvtParaLen, rptEvtPara}
    STATUS current
    DESCRIPTION
    "Trap of PerEvt: OTU0 SM Incoming Alignment Errored Second."
    ::= { optixTrapsPER 16224 }

--  1.3.6.1.4.1.2011.2.25.3.40.40.30.16225
    perEvtOtu0Biaes NOTIFICATION-TYPE
    OBJECTS { rptEvtPeriod, rptEvtValue, rptEvtVldty, rptEvtDateTime, rptEvtObjType, rptEvtParaLen, rptEvtPara}
    STATUS current
    DESCRIPTION
    "Trap of PerEvt: OTU0 SM Backward Incoming Alignment Errored Second."
    ::= { optixTrapsPER 16225 }

--  1.3.6.1.4.1.2011.2.25.3.40.40.30.16226
    perEvtOtu0Bber NOTIFICATION-TYPE
    OBJECTS { rptEvtPeriod, rptEvtValue, rptEvtVldty, rptEvtDateTime, rptEvtObjType, rptEvtParaLen, rptEvtPara}
    STATUS current
    DESCRIPTION
    "Trap of PerEvt: OTU0 SM Background Block Error Ratio."
    ::= { optixTrapsPER 16226 }

--  1.3.6.1.4.1.2011.2.25.3.40.40.30.16227
    perEvtOtu0Febbe NOTIFICATION-TYPE
    OBJECTS { rptEvtPeriod, rptEvtValue, rptEvtVldty, rptEvtDateTime, rptEvtObjType, rptEvtParaLen, rptEvtPara}
    STATUS current
    DESCRIPTION
    "Trap of PerEvt: OTU0 SM Far Background Block Error."
    ::= { optixTrapsPER 16227 }

--  1.3.6.1.4.1.2011.2.25.3.40.40.30.16228
    perEvtOtu0Febber NOTIFICATION-TYPE
    OBJECTS { rptEvtPeriod, rptEvtValue, rptEvtVldty, rptEvtDateTime, rptEvtObjType, rptEvtParaLen, rptEvtPara}
    STATUS current
    DESCRIPTION
    "Trap of PerEvt: OTU0 SM Far Background Block Error Ratio."
    ::= { optixTrapsPER 16228 }

--  1.3.6.1.4.1.2011.2.25.3.40.40.30.16229
    perEvtOtu0Es NOTIFICATION-TYPE
    OBJECTS { rptEvtPeriod, rptEvtValue, rptEvtVldty, rptEvtDateTime, rptEvtObjType, rptEvtParaLen, rptEvtPara}
    STATUS current
    DESCRIPTION
    "Trap of PerEvt: OTU0 SM Errored Second."
    ::= { optixTrapsPER 16229 }

--  1.3.6.1.4.1.2011.2.25.3.40.40.30.14922
    perEvtMemusagemax NOTIFICATION-TYPE
    OBJECTS { rptEvtPeriod, rptEvtValue, rptEvtVldty, rptEvtDateTime, rptEvtObjType, rptEvtParaLen, rptEvtPara}
    STATUS current
    DESCRIPTION
    "Trap of PerEvt: Maximum value of memory usage."
    ::= { optixTrapsPER 14922 }

--  1.3.6.1.4.1.2011.2.25.3.40.40.30.14923
    perEvtMemusagemin NOTIFICATION-TYPE
    OBJECTS { rptEvtPeriod, rptEvtValue, rptEvtVldty, rptEvtDateTime, rptEvtObjType, rptEvtParaLen, rptEvtPara}
    STATUS current
    DESCRIPTION
    "Trap of PerEvt: Minimum value of memory usage."
    ::= { optixTrapsPER 14923 }

--  1.3.6.1.4.1.2011.2.25.3.40.40.30.14924
    perEvtMemusagecur NOTIFICATION-TYPE
    OBJECTS { rptEvtPeriod, rptEvtValue, rptEvtVldty, rptEvtDateTime, rptEvtObjType, rptEvtParaLen, rptEvtPara}
    STATUS current
    DESCRIPTION
    "Trap of PerEvt: Current value of memory usage."
    ::= { optixTrapsPER 14924 }

-- R21C10SPC100
--  1.3.6.1.4.1.2011.2.25.3.40.40.30.16361
    perEvtAvgstdptpoffset NOTIFICATION-TYPE
    OBJECTS { rptEvtPeriod, rptEvtValue, rptEvtVldty, rptEvtDateTime, rptEvtObjType, rptEvtParaLen, rptEvtPara}
    STATUS current
    DESCRIPTION
    "Trap of PerEvt: 11/5000 Æ´Òô ·­Òë
Average value of the absolute time reference comparison result."
    ::= { optixTrapsPER 16361 }

--  1.3.6.1.4.1.2011.2.25.3.40.40.30.16362
    perEvtMinstdptpoffset NOTIFICATION-TYPE
    OBJECTS { rptEvtPeriod, rptEvtValue, rptEvtVldty, rptEvtDateTime, rptEvtObjType, rptEvtParaLen, rptEvtPara}
    STATUS current
    DESCRIPTION
    "Trap of PerEvt: Minimum value of the absolute time reference comparison result."
    ::= { optixTrapsPER 16362 }

--  1.3.6.1.4.1.2011.2.25.3.40.40.30.16363
    perEvtMaxstdptpoffset NOTIFICATION-TYPE
    OBJECTS { rptEvtPeriod, rptEvtValue, rptEvtVldty, rptEvtDateTime, rptEvtObjType, rptEvtParaLen, rptEvtPara}
    STATUS current
    DESCRIPTION
    "Trap of PerEvt: Maximum value of the absolute time reference comparison result."
    ::= { optixTrapsPER 16363 }

--  1.3.6.1.4.1.2011.2.25.3.40.40.30.16367
    perEvtRecFreqOffsetcur NOTIFICATION-TYPE
    OBJECTS { rptEvtPeriod, rptEvtValue, rptEvtVldty, rptEvtDateTime, rptEvtObjType, rptEvtParaLen, rptEvtPara}
    STATUS current
    DESCRIPTION
    "Trap of PerEvt: Current offset of the laser receive frequency."
    ::= { optixTrapsPER 16367 }

--  1.3.6.1.4.1.2011.2.25.3.40.40.30.16368
    perEvtOsnrmax NOTIFICATION-TYPE
    OBJECTS { rptEvtPeriod, rptEvtValue, rptEvtVldty, rptEvtDateTime, rptEvtObjType, rptEvtParaLen, rptEvtPara}
    STATUS current
    DESCRIPTION
    "Trap of PerEvt: Maximum OSNR."
    ::= { optixTrapsPER 16368 }

--  1.3.6.1.4.1.2011.2.25.3.40.40.30.16369
    perEvtOsnrmin NOTIFICATION-TYPE
    OBJECTS { rptEvtPeriod, rptEvtValue, rptEvtVldty, rptEvtDateTime, rptEvtObjType, rptEvtParaLen, rptEvtPara}
    STATUS current
    DESCRIPTION
    "Trap of PerEvt: Minimum OSNR."
    ::= { optixTrapsPER 16369 }

--  1.3.6.1.4.1.2011.2.25.3.40.40.30.16370
    perEvtOsnrcur NOTIFICATION-TYPE
    OBJECTS { rptEvtPeriod, rptEvtValue, rptEvtVldty, rptEvtDateTime, rptEvtObjType, rptEvtParaLen, rptEvtPara}
    STATUS current
    DESCRIPTION
    "Trap of PerEvt: Current OSNR."
    ::= { optixTrapsPER 16370 }

--  1.3.6.1.4.1.2011.2.25.3.40.40.30.16371
    perEvtRecFreqOffsetmin NOTIFICATION-TYPE
    OBJECTS { rptEvtPeriod, rptEvtValue, rptEvtVldty, rptEvtDateTime, rptEvtObjType, rptEvtParaLen, rptEvtPara}
    STATUS current
    DESCRIPTION
    "Trap of PerEvt: Minimum offset of the laser receive frequency."
    ::= { optixTrapsPER 16371 }

--  1.3.6.1.4.1.2011.2.25.3.40.40.30.16372
    perEvtRecFreqOffsetmax NOTIFICATION-TYPE
    OBJECTS { rptEvtPeriod, rptEvtValue, rptEvtVldty, rptEvtDateTime, rptEvtObjType, rptEvtParaLen, rptEvtPara}
    STATUS current
    DESCRIPTION
    "Trap of PerEvt: Maximum offset of the laser receive frequency."
    ::= { optixTrapsPER 16372 }

--  1.3.6.1.4.1.2011.2.25.3.40.40.30.16373
    perEvtDelayMeasureAvg NOTIFICATION-TYPE
    OBJECTS { rptEvtPeriod, rptEvtValue, rptEvtVldty, rptEvtDateTime, rptEvtObjType, rptEvtParaLen, rptEvtPara}
    STATUS current
    DESCRIPTION
    "Trap of PerEvt: Average delay measurement value."
    ::= { optixTrapsPER 16373 }

--  1.3.6.1.4.1.2011.2.25.3.40.40.30.16374
    perEvtDelayMeasureCur NOTIFICATION-TYPE
    OBJECTS { rptEvtPeriod, rptEvtValue, rptEvtVldty, rptEvtDateTime, rptEvtObjType, rptEvtParaLen, rptEvtPara}
    STATUS current
    DESCRIPTION
    "Trap of PerEvt: Real-time delay measurement value."
    ::= { optixTrapsPER 16374 }

--  1.3.6.1.4.1.2011.2.25.3.40.40.30.16375
    perEvtDelayMeasureMin NOTIFICATION-TYPE
    OBJECTS { rptEvtPeriod, rptEvtValue, rptEvtVldty, rptEvtDateTime, rptEvtObjType, rptEvtParaLen, rptEvtPara}
    STATUS current
    DESCRIPTION
    "Trap of PerEvt: Minimum delay measurement value."
    ::= { optixTrapsPER 16375 }

--  1.3.6.1.4.1.2011.2.25.3.40.40.30.16376
    perEvtDelayMeasureMax NOTIFICATION-TYPE
    OBJECTS { rptEvtPeriod, rptEvtValue, rptEvtVldty, rptEvtDateTime, rptEvtObjType, rptEvtParaLen, rptEvtPara}
    STATUS current
    DESCRIPTION
    "Trap of PerEvt: Maximum delay measurement value."
    ::= { optixTrapsPER 16376 }

--  1.3.6.1.4.1.2011.2.25.3.40.40.30.16391
    perEvtTdccurAvgY NOTIFICATION-TYPE
    OBJECTS { rptEvtPeriod, rptEvtValue, rptEvtVldty, rptEvtDateTime, rptEvtObjType, rptEvtParaLen, rptEvtPara}
    STATUS current
    DESCRIPTION
    "Trap of PerEvt: Average dispersion compensation."
    ::= { optixTrapsPER 16391 }

--  1.3.6.1.4.1.2011.2.25.3.40.40.30.16398
    perEvtLswfrequencyMinY NOTIFICATION-TYPE
    OBJECTS { rptEvtPeriod, rptEvtValue, rptEvtVldty, rptEvtDateTime, rptEvtObjType, rptEvtParaLen, rptEvtPara}
    STATUS current
    DESCRIPTION
    "Trap of PerEvt: Minimum central frequency of a wavelength."
    ::= { optixTrapsPER 16398 }

--  1.3.6.1.4.1.2011.2.25.3.40.40.30.16399
    perEvtLswfrequencyMaxY NOTIFICATION-TYPE
    OBJECTS { rptEvtPeriod, rptEvtValue, rptEvtVldty, rptEvtDateTime, rptEvtObjType, rptEvtParaLen, rptEvtPara}
    STATUS current
    DESCRIPTION
    "Trap of PerEvt: Maximum central frequency of a wavelength."
    ::= { optixTrapsPER 16399 }

--  1.3.6.1.4.1.2011.2.25.3.40.40.30.16400
    perEvtLswfrequencyAvgY NOTIFICATION-TYPE
    OBJECTS { rptEvtPeriod, rptEvtValue, rptEvtVldty, rptEvtDateTime, rptEvtObjType, rptEvtParaLen, rptEvtPara}
    STATUS current
    DESCRIPTION
    "Trap of PerEvt: Average central frequency of a wavelength."
    ::= { optixTrapsPER 16400 }

--  1.3.6.1.4.1.2011.2.25.3.40.40.30.16403
    perEvtLstmpcurAvgY NOTIFICATION-TYPE
    OBJECTS { rptEvtPeriod, rptEvtValue, rptEvtVldty, rptEvtDateTime, rptEvtObjType, rptEvtParaLen, rptEvtPara}
    STATUS current
    DESCRIPTION
    "Trap of PerEvt: Average laser working temperature."
    ::= { optixTrapsPER 16403 }

--  1.3.6.1.4.1.2011.2.25.3.40.40.30.16406
    perEvtLsoopcurAvgY NOTIFICATION-TYPE
    OBJECTS { rptEvtPeriod, rptEvtValue, rptEvtVldty, rptEvtDateTime, rptEvtObjType, rptEvtParaLen, rptEvtPara}
    STATUS current
    DESCRIPTION
    "Trap of PerEvt: Average laser output of power."
    ::= { optixTrapsPER 16406 }

--  1.3.6.1.4.1.2011.2.25.3.40.40.30.16409
    perEvtLsiopcurAvgY NOTIFICATION-TYPE
    OBJECTS { rptEvtPeriod, rptEvtValue, rptEvtVldty, rptEvtDateTime, rptEvtObjType, rptEvtParaLen, rptEvtPara}
    STATUS current
    DESCRIPTION
    "Trap of PerEvt: Average laser input of power."
    ::= { optixTrapsPER 16409 }

--  1.3.6.1.4.1.2011.2.25.3.40.40.30.16412
    perEvtLsbiascurAvgY NOTIFICATION-TYPE
    OBJECTS { rptEvtPeriod, rptEvtValue, rptEvtVldty, rptEvtDateTime, rptEvtObjType, rptEvtParaLen, rptEvtPara}
    STATUS current
    DESCRIPTION
    "Trap of PerEvt: Average laser bias current."
    ::= { optixTrapsPER 16412 }

--  1.3.6.1.4.1.2011.2.25.3.40.40.30.16415
    perEvtLaneLsoopAvgY NOTIFICATION-TYPE
    OBJECTS { rptEvtPeriod, rptEvtValue, rptEvtVldty, rptEvtDateTime, rptEvtObjType, rptEvtParaLen, rptEvtPara}
    STATUS current
    DESCRIPTION
    "Trap of PerEvt: Average laser output power on the sub-channel."
    ::= { optixTrapsPER 16415 }

--  1.3.6.1.4.1.2011.2.25.3.40.40.30.16418
    perEvtLaneLsiopAvgY NOTIFICATION-TYPE
    OBJECTS { rptEvtPeriod, rptEvtValue, rptEvtVldty, rptEvtDateTime, rptEvtObjType, rptEvtParaLen, rptEvtPara}
    STATUS current
    DESCRIPTION
    "Trap of PerEvt: Average laser input power on the sub-channel."
    ::= { optixTrapsPER 16418 }

--  1.3.6.1.4.1.2011.2.25.3.40.40.30.16421
    perEvtLaneLsbiasAvgY NOTIFICATION-TYPE
    OBJECTS { rptEvtPeriod, rptEvtValue, rptEvtVldty, rptEvtDateTime, rptEvtObjType, rptEvtParaLen, rptEvtPara}
    STATUS current
    DESCRIPTION
    "Trap of PerEvt: Average laser bias current on the sub-channel."
    ::= { optixTrapsPER 16421 }

--  1.3.6.1.4.1.2011.2.25.3.40.40.30.16424
    perEvtXcstmpcurAvgY NOTIFICATION-TYPE
    OBJECTS { rptEvtPeriod, rptEvtValue, rptEvtVldty, rptEvtDateTime, rptEvtObjType, rptEvtParaLen, rptEvtPara}
    STATUS current
    DESCRIPTION
    "Trap of PerEvt: Average board temperature."
    ::= { optixTrapsPER 16424 }

--  1.3.6.1.4.1.2011.2.25.3.40.40.30.16433
    perEvtFanspeedcurAvgY NOTIFICATION-TYPE
    OBJECTS { rptEvtPeriod, rptEvtValue, rptEvtVldty, rptEvtDateTime, rptEvtObjType, rptEvtParaLen, rptEvtPara}
    STATUS current
    DESCRIPTION
    "Trap of PerEvt: Average fan speed."
    ::= { optixTrapsPER 16433 }

--  1.3.6.1.4.1.2011.2.25.3.40.40.30.16434
    perEvtBdUsedPowerMinY NOTIFICATION-TYPE
    OBJECTS { rptEvtPeriod, rptEvtValue, rptEvtVldty, rptEvtDateTime, rptEvtObjType, rptEvtParaLen, rptEvtPara}
    STATUS current
    DESCRIPTION
    "Trap of PerEvt: Minimum power consumption of the board."
    ::= { optixTrapsPER 16434 }

--  1.3.6.1.4.1.2011.2.25.3.40.40.30.16435
    perEvtBdUsedPowerMaxY NOTIFICATION-TYPE
    OBJECTS { rptEvtPeriod, rptEvtValue, rptEvtVldty, rptEvtDateTime, rptEvtObjType, rptEvtParaLen, rptEvtPara}
    STATUS current
    DESCRIPTION
    "Trap of PerEvt: Maximum power consumption of the board."
    ::= { optixTrapsPER 16435 }

--  1.3.6.1.4.1.2011.2.25.3.40.40.30.16436
    perEvtBdUsedPowerAvgY NOTIFICATION-TYPE
    OBJECTS { rptEvtPeriod, rptEvtValue, rptEvtVldty, rptEvtDateTime, rptEvtObjType, rptEvtParaLen, rptEvtPara}
    STATUS current
    DESCRIPTION
    "Trap of PerEvt: Average power consumption of the board."
    ::= { optixTrapsPER 16436 }

--  1.3.6.1.4.1.2011.2.25.3.40.40.30.16439
    perEvtInputCurrentAvgY NOTIFICATION-TYPE
    OBJECTS { rptEvtPeriod, rptEvtValue, rptEvtVldty, rptEvtDateTime, rptEvtObjType, rptEvtParaLen, rptEvtPara}
    STATUS current
    DESCRIPTION
    "Trap of PerEvt: Average input current."
    ::= { optixTrapsPER 16439 }

--  1.3.6.1.4.1.2011.2.25.3.40.40.30.16442
    perEvtInputvoltminAvgY NOTIFICATION-TYPE
    OBJECTS { rptEvtPeriod, rptEvtValue, rptEvtVldty, rptEvtDateTime, rptEvtObjType, rptEvtParaLen, rptEvtPara}
    STATUS current
    DESCRIPTION
    "Trap of PerEvt: Average input voltage."
    ::= { optixTrapsPER 16442 }

--  1.3.6.1.4.1.2011.2.25.3.40.40.30.16445
    perEvtOutputcurrentAvgY NOTIFICATION-TYPE
    OBJECTS { rptEvtPeriod, rptEvtValue, rptEvtVldty, rptEvtDateTime, rptEvtObjType, rptEvtParaLen, rptEvtPara}
    STATUS current
    DESCRIPTION
    "Trap of PerEvt: Average output current."
    ::= { optixTrapsPER 16445 }

--  1.3.6.1.4.1.2011.2.25.3.40.40.30.16448
    perEvtOutputvoltAvgY NOTIFICATION-TYPE
    OBJECTS { rptEvtPeriod, rptEvtValue, rptEvtVldty, rptEvtDateTime, rptEvtObjType, rptEvtParaLen, rptEvtPara}
    STATUS current
    DESCRIPTION
    "Trap of PerEvt: Average output voltage."
    ::= { optixTrapsPER 16448 }

--  1.3.6.1.4.1.2011.2.25.3.40.40.30.16468
    perEvtLsvolavgY NOTIFICATION-TYPE
    OBJECTS { rptEvtPeriod, rptEvtValue, rptEvtVldty, rptEvtDateTime, rptEvtObjType, rptEvtParaLen, rptEvtPara}
    STATUS current
    DESCRIPTION
    "Trap of PerEvt: Average laser voltage."
    ::= { optixTrapsPER 16468 }

--  1.3.6.1.4.1.2011.2.25.3.40.40.30.16469
    perEvtOsnravg NOTIFICATION-TYPE
    OBJECTS { rptEvtPeriod, rptEvtValue, rptEvtVldty, rptEvtDateTime, rptEvtObjType, rptEvtParaLen, rptEvtPara}
    STATUS current
    DESCRIPTION
    "Trap of PerEvt: Average optical signal-to-noise ratio."
    ::= { optixTrapsPER 16469 }

--  1.3.6.1.4.1.2011.2.25.3.40.40.30.16470
    perEvtIctmpavg NOTIFICATION-TYPE
    OBJECTS { rptEvtPeriod, rptEvtValue, rptEvtVldty, rptEvtDateTime, rptEvtObjType, rptEvtParaLen, rptEvtPara}
    STATUS current
    DESCRIPTION
    "Trap of PerEvt: Average integrated circuit temperature."
    ::= { optixTrapsPER 16470 }

--  1.3.6.1.4.1.2011.2.25.3.40.40.30.16471
    perEvtFclsopavg NOTIFICATION-TYPE
    OBJECTS { rptEvtPeriod, rptEvtValue, rptEvtVldty, rptEvtDateTime, rptEvtObjType, rptEvtParaLen, rptEvtPara}
    STATUS current
    DESCRIPTION
    "Trap of PerEvt: Average single-channel input optical power."
    ::= { optixTrapsPER 16471 }

--  1.3.6.1.4.1.2011.2.25.3.40.40.30.16472
    perEvtFswsnravg NOTIFICATION-TYPE
    OBJECTS { rptEvtPeriod, rptEvtValue, rptEvtVldty, rptEvtDateTime, rptEvtObjType, rptEvtParaLen, rptEvtPara}
    STATUS current
    DESCRIPTION
    "Trap of PerEvt: Average single-wavelength OSNR."
    ::= { optixTrapsPER 16472 }

--  1.3.6.1.4.1.2011.2.25.3.40.40.30.16473
    perEvtFpclswloavg NOTIFICATION-TYPE
    OBJECTS { rptEvtPeriod, rptEvtValue, rptEvtVldty, rptEvtDateTime, rptEvtObjType, rptEvtParaLen, rptEvtPara}
    STATUS current
    DESCRIPTION
    "Trap of PerEvt: Average Per-Channel Laser WaveLength Offset Value."
    ::= { optixTrapsPER 16473 }

--  1.3.6.1.4.1.2011.2.25.3.40.40.30.16474
    perEvtSumiopavg NOTIFICATION-TYPE
    OBJECTS { rptEvtPeriod, rptEvtValue, rptEvtVldty, rptEvtDateTime, rptEvtObjType, rptEvtParaLen, rptEvtPara}
    STATUS current
    DESCRIPTION
    "Trap of PerEvt: Average total laser input power."
    ::= { optixTrapsPER 16474 }

--  1.3.6.1.4.1.2011.2.25.3.40.40.30.16475
    perEvtSumoopavg NOTIFICATION-TYPE
    OBJECTS { rptEvtPeriod, rptEvtValue, rptEvtVldty, rptEvtDateTime, rptEvtObjType, rptEvtParaLen, rptEvtPara}
    STATUS current
    DESCRIPTION
    "Trap of PerEvt: Average total laser output power."
    ::= { optixTrapsPER 16475 }

--  1.3.6.1.4.1.2011.2.25.3.40.40.30.16476
    perEvtFswoopavg NOTIFICATION-TYPE
    OBJECTS { rptEvtPeriod, rptEvtValue, rptEvtVldty, rptEvtDateTime, rptEvtObjType, rptEvtParaLen, rptEvtPara}
    STATUS current
    DESCRIPTION
    "Trap of PerEvt: Average single-wavelength output optical power."
    ::= { optixTrapsPER 16476 }

--  1.3.6.1.4.1.2011.2.25.3.40.40.30.16477
    perEvtFswsnlavg NOTIFICATION-TYPE
    OBJECTS { rptEvtPeriod, rptEvtValue, rptEvtVldty, rptEvtDateTime, rptEvtObjType, rptEvtParaLen, rptEvtPara}
    STATUS current
    DESCRIPTION
    "Trap of PerEvt: Average single-wavelength OSNR degradation amount."
    ::= { optixTrapsPER 16477 }

--  1.3.6.1.4.1.2011.2.25.3.40.40.30.16478
    perEvtFswiopavg NOTIFICATION-TYPE
    OBJECTS { rptEvtPeriod, rptEvtValue, rptEvtVldty, rptEvtDateTime, rptEvtObjType, rptEvtParaLen, rptEvtPara}
    STATUS current
    DESCRIPTION
    "Trap of PerEvt: Average single-wavelength input optical power."
    ::= { optixTrapsPER 16478 }

--  1.3.6.1.4.1.2011.2.25.3.40.40.30.16479
    perEvtAainpavg NOTIFICATION-TYPE
    OBJECTS { rptEvtPeriod, rptEvtValue, rptEvtVldty, rptEvtDateTime, rptEvtObjType, rptEvtParaLen, rptEvtPara}
    STATUS current
    DESCRIPTION
    "Trap of PerEvt: Average value of the average input noise power."
    ::= { optixTrapsPER 16479 }

--  1.3.6.1.4.1.2011.2.25.3.40.40.30.16480
    perEvtAaispavg NOTIFICATION-TYPE
    OBJECTS { rptEvtPeriod, rptEvtValue, rptEvtVldty, rptEvtDateTime, rptEvtObjType, rptEvtParaLen, rptEvtPara}
    STATUS current
    DESCRIPTION
    "Trap of PerEvt: Average value of the average input signal power."
    ::= { optixTrapsPER 16480 }

--  1.3.6.1.4.1.2011.2.25.3.40.40.30.16481
    perEvtAaonpavg NOTIFICATION-TYPE
    OBJECTS { rptEvtPeriod, rptEvtValue, rptEvtVldty, rptEvtDateTime, rptEvtObjType, rptEvtParaLen, rptEvtPara}
    STATUS current
    DESCRIPTION
    "Trap of PerEvt: Average value of the average output noise power."
    ::= { optixTrapsPER 16481 }

--  1.3.6.1.4.1.2011.2.25.3.40.40.30.16482
    perEvtAaospavg NOTIFICATION-TYPE
    OBJECTS { rptEvtPeriod, rptEvtValue, rptEvtVldty, rptEvtDateTime, rptEvtObjType, rptEvtParaLen, rptEvtPara}
    STATUS current
    DESCRIPTION
    "Trap of PerEvt: Average value of the average output signal power."
    ::= { optixTrapsPER 16482 }

--  1.3.6.1.4.1.2011.2.25.3.40.40.30.16483
    perEvtWcvavg NOTIFICATION-TYPE
    OBJECTS { rptEvtPeriod, rptEvtValue, rptEvtVldty, rptEvtDateTime, rptEvtObjType, rptEvtParaLen, rptEvtPara}
    STATUS current
    DESCRIPTION
    "Trap of PerEvt: Laser Working Current Average Value."
    ::= { optixTrapsPER 16483 }

--  1.3.6.1.4.1.2011.2.25.3.40.40.30.16484
    perEvtCcvavg NOTIFICATION-TYPE
    OBJECTS { rptEvtPeriod, rptEvtValue, rptEvtVldty, rptEvtDateTime, rptEvtObjType, rptEvtParaLen, rptEvtPara}
    STATUS current
    DESCRIPTION
    "Trap of PerEvt: Laser Cooling Current Average Value."
    ::= { optixTrapsPER 16484 }

--  1.3.6.1.4.1.2011.2.25.3.40.40.30.16485
    perEvtBcvavg NOTIFICATION-TYPE
    OBJECTS { rptEvtPeriod, rptEvtValue, rptEvtVldty, rptEvtDateTime, rptEvtObjType, rptEvtParaLen, rptEvtPara}
    STATUS current
    DESCRIPTION
    "Trap of PerEvt: Laser Back Current Average Value."
    ::= { optixTrapsPER 16485 }

--  1.3.6.1.4.1.2011.2.25.3.40.40.30.16486
    perEvtEdtmpavg NOTIFICATION-TYPE
    OBJECTS { rptEvtPeriod, rptEvtValue, rptEvtVldty, rptEvtDateTime, rptEvtObjType, rptEvtParaLen, rptEvtPara}
    STATUS current
    DESCRIPTION
    "Trap of PerEvt: Laser Temperature Average Value."
    ::= { optixTrapsPER 16486 }

--  1.3.6.1.4.1.2011.2.25.3.40.40.30.16487
    perEvtFecBefCorErmax NOTIFICATION-TYPE
    OBJECTS { rptEvtPeriod, rptEvtValue, rptEvtVldty, rptEvtDateTime, rptEvtObjType, rptEvtParaLen, rptEvtPara}
    STATUS current
    DESCRIPTION
    "Trap of PerEvt: Maximum BER before FEC."
    ::= { optixTrapsPER 16487 }

--  1.3.6.1.4.1.2011.2.25.3.40.40.30.16488
    perEvtFecBefCorErmin NOTIFICATION-TYPE
    OBJECTS { rptEvtPeriod, rptEvtValue, rptEvtVldty, rptEvtDateTime, rptEvtObjType, rptEvtParaLen, rptEvtPara}
    STATUS current
    DESCRIPTION
    "Trap of PerEvt: Minimum BER before FEC."
    ::= { optixTrapsPER 16488 }

--  1.3.6.1.4.1.2011.2.25.3.40.40.30.16489
    perEvtFecAftCorErmin NOTIFICATION-TYPE
    OBJECTS { rptEvtPeriod, rptEvtValue, rptEvtVldty, rptEvtDateTime, rptEvtObjType, rptEvtParaLen, rptEvtPara}
    STATUS current
    DESCRIPTION
    "Trap of PerEvt: Minimum BER after FEC."
    ::= { optixTrapsPER 16489 }

--  1.3.6.1.4.1.2011.2.25.3.40.40.30.16490
    perEvtFecAftCorErmax NOTIFICATION-TYPE
    OBJECTS { rptEvtPeriod, rptEvtValue, rptEvtVldty, rptEvtDateTime, rptEvtObjType, rptEvtParaLen, rptEvtPara}
    STATUS current
    DESCRIPTION
    "Trap of PerEvt: Maximum BER after FEC."
    ::= { optixTrapsPER 16490 }

--  1.3.6.1.4.1.2011.2.25.3.40.40.30.16491
    perEvtIcclcavg NOTIFICATION-TYPE
    OBJECTS { rptEvtPeriod, rptEvtValue, rptEvtVldty, rptEvtDateTime, rptEvtObjType, rptEvtParaLen, rptEvtPara}
    STATUS current
    DESCRIPTION
    "Trap of PerEvt: ICCLCAVG."
    ::= { optixTrapsPER 16491 }

--  1.3.6.1.4.1.2011.2.25.3.40.40.30.16492
    perEvtGainavg NOTIFICATION-TYPE
    OBJECTS { rptEvtPeriod, rptEvtValue, rptEvtVldty, rptEvtDateTime, rptEvtObjType, rptEvtParaLen, rptEvtPara}
    STATUS current
    DESCRIPTION
    "Trap of PerEvt: Average Gain."
    ::= { optixTrapsPER 16492 }

--  1.3.6.1.4.1.2011.2.25.3.40.40.30.16238
    perEvtMemoccupyave NOTIFICATION-TYPE
    OBJECTS { rptEvtPeriod, rptEvtValue, rptEvtVldty, rptEvtDateTime, rptEvtObjType, rptEvtParaLen, rptEvtPara}
    STATUS current
    DESCRIPTION
    "Trap of PerEvt: Average number of bytes used in the memory."
    ::= { optixTrapsPER 16238 }

--  1.3.6.1.4.1.2011.2.25.3.40.40.30.16430
    perEvtCpuusagecurAvgY NOTIFICATION-TYPE
    OBJECTS { rptEvtPeriod, rptEvtValue, rptEvtVldty, rptEvtDateTime, rptEvtObjType, rptEvtParaLen, rptEvtPara}
    STATUS current
    DESCRIPTION
    "Trap of PerEvt: Average CPU usage."
    ::= { optixTrapsPER 16430 }

--  1.3.6.1.4.1.2011.2.25.3.40.40.30.16493
    perEvtLssumiopmax NOTIFICATION-TYPE
    OBJECTS { rptEvtPeriod, rptEvtValue, rptEvtVldty, rptEvtDateTime, rptEvtObjType, rptEvtParaLen, rptEvtPara}
    STATUS current
    DESCRIPTION
    "Trap of PerEvt: Maximum total input optical power of the Light Sensor."
    ::= { optixTrapsPER 16493 }

--  1.3.6.1.4.1.2011.2.25.3.40.40.30.16494
    perEvtLssumiopmin NOTIFICATION-TYPE
    OBJECTS { rptEvtPeriod, rptEvtValue, rptEvtVldty, rptEvtDateTime, rptEvtObjType, rptEvtParaLen, rptEvtPara}
    STATUS current
    DESCRIPTION
    "Trap of PerEvt: Minimum total input optical power of the Light Sensor."
    ::= { optixTrapsPER 16494 }

--  1.3.6.1.4.1.2011.2.25.3.40.40.30.16495
    perEvtLssumiopcur NOTIFICATION-TYPE
    OBJECTS { rptEvtPeriod, rptEvtValue, rptEvtVldty, rptEvtDateTime, rptEvtObjType, rptEvtParaLen, rptEvtPara}
    STATUS current
    DESCRIPTION
    "Trap of PerEvt: Current total input optical power of the Light Sensor."
    ::= { optixTrapsPER 16495 }

--  1.3.6.1.4.1.2011.2.25.3.40.40.30.16496
    perEvtMemavailmax NOTIFICATION-TYPE
    OBJECTS { rptEvtPeriod, rptEvtValue, rptEvtVldty, rptEvtDateTime, rptEvtObjType, rptEvtParaLen, rptEvtPara}
    STATUS current
    DESCRIPTION
    "Trap of PerEvt: Maximum number of bytes available in the memory."
    ::= { optixTrapsPER 16496 }

--  1.3.6.1.4.1.2011.2.25.3.40.40.30.16497
    perEvtMemavailmin NOTIFICATION-TYPE
    OBJECTS { rptEvtPeriod, rptEvtValue, rptEvtVldty, rptEvtDateTime, rptEvtObjType, rptEvtParaLen, rptEvtPara}
    STATUS current
    DESCRIPTION
    "Trap of PerEvt: Minimum number of bytes available in the memory."
    ::= { optixTrapsPER 16497 }

--  1.3.6.1.4.1.2011.2.25.3.40.40.30.16498
    perEvtMemavailcur NOTIFICATION-TYPE
    OBJECTS { rptEvtPeriod, rptEvtValue, rptEvtVldty, rptEvtDateTime, rptEvtObjType, rptEvtParaLen, rptEvtPara}
    STATUS current
    DESCRIPTION
    "Trap of PerEvt: Current number of bytes available in the memory."
    ::= { optixTrapsPER 16498 }

--  1.3.6.1.4.1.2011.2.25.3.40.40.30.16499
    perEvtMemavailavg NOTIFICATION-TYPE
    OBJECTS { rptEvtPeriod, rptEvtValue, rptEvtVldty, rptEvtDateTime, rptEvtObjType, rptEvtParaLen, rptEvtPara}
    STATUS current
    DESCRIPTION
    "Trap of PerEvt: Average number of bytes available in the memory."
    ::= { optixTrapsPER 16499 }

--  1.3.6.1.4.1.2011.2.25.3.40.40.30.16500
    perEvtSubcardtmpavg NOTIFICATION-TYPE
    OBJECTS { rptEvtPeriod, rptEvtValue, rptEvtVldty, rptEvtDateTime, rptEvtObjType, rptEvtParaLen, rptEvtPara}
    STATUS current
    DESCRIPTION
    "Trap of PerEvt: Subcard Temperature Average Value."
    ::= { optixTrapsPER 16500 }

--  1.3.6.1.4.1.2011.2.25.3.40.40.30.16525
    perEvtLsclcavg NOTIFICATION-TYPE
    OBJECTS { rptEvtPeriod, rptEvtValue, rptEvtVldty, rptEvtDateTime, rptEvtObjType, rptEvtParaLen, rptEvtPara}
    STATUS current
    DESCRIPTION
    "Trap of PerEvt: Average cooling current of the laser."
    ::= { optixTrapsPER 16525 }

--  1.3.6.1.4.1.2011.2.25.3.40.40.30.16531
    perEvtShelfPwrMax NOTIFICATION-TYPE
    OBJECTS { rptEvtPeriod, rptEvtValue, rptEvtVldty, rptEvtDateTime, rptEvtObjType, rptEvtParaLen, rptEvtPara}
    STATUS current
    DESCRIPTION
    "Trap of PerEvt: Maximum shelf power."
    ::= { optixTrapsPER 16531 }

--  1.3.6.1.4.1.2011.2.25.3.40.40.30.16532
    perEvtShelfPwrMin NOTIFICATION-TYPE
    OBJECTS { rptEvtPeriod, rptEvtValue, rptEvtVldty, rptEvtDateTime, rptEvtObjType, rptEvtParaLen, rptEvtPara}
    STATUS current
    DESCRIPTION
    "Trap of PerEvt: Minimum shelf power."
    ::= { optixTrapsPER 16532 }

--  1.3.6.1.4.1.2011.2.25.3.40.40.30.16533
    perEvtShelfPwrAvg NOTIFICATION-TYPE
    OBJECTS { rptEvtPeriod, rptEvtValue, rptEvtVldty, rptEvtDateTime, rptEvtObjType, rptEvtParaLen, rptEvtPara}
    STATUS current
    DESCRIPTION
    "Trap of PerEvt: Average shelf power."
    ::= { optixTrapsPER 16533 }

--  1.3.6.1.4.1.2011.2.25.3.40.40.30.16534
    perEvtShelfPwrCur NOTIFICATION-TYPE
    OBJECTS { rptEvtPeriod, rptEvtValue, rptEvtVldty, rptEvtDateTime, rptEvtObjType, rptEvtParaLen, rptEvtPara}
    STATUS current
    DESCRIPTION
    "Trap of PerEvt: Current shelf power."
    ::= { optixTrapsPER 16534 }

--  1.3.6.1.4.1.2011.2.25.3.40.40.30.16535
    perEvtLsumiopmax NOTIFICATION-TYPE
    OBJECTS { rptEvtPeriod, rptEvtValue, rptEvtVldty, rptEvtDateTime, rptEvtObjType, rptEvtParaLen, rptEvtPara}
    STATUS current
    DESCRIPTION
    "Trap of PerEvt: Maximum total input optical power of the L-band."
    ::= { optixTrapsPER 16535 }

--  1.3.6.1.4.1.2011.2.25.3.40.40.30.16536
    perEvtLsumiopmin NOTIFICATION-TYPE
    OBJECTS { rptEvtPeriod, rptEvtValue, rptEvtVldty, rptEvtDateTime, rptEvtObjType, rptEvtParaLen, rptEvtPara}
    STATUS current
    DESCRIPTION
    "Trap of PerEvt: Minimum total input optical power of the L-band."
    ::= { optixTrapsPER 16536 }

--  1.3.6.1.4.1.2011.2.25.3.40.40.30.16537
    perEvtLsumiopcur NOTIFICATION-TYPE
    OBJECTS { rptEvtPeriod, rptEvtValue, rptEvtVldty, rptEvtDateTime, rptEvtObjType, rptEvtParaLen, rptEvtPara}
    STATUS current
    DESCRIPTION
    "Trap of PerEvt: Current total input optical power of the L-band."
    ::= { optixTrapsPER 16537 }

--  1.3.6.1.4.1.2011.2.25.3.40.40.30.16538
    perEvtLsumiopavg NOTIFICATION-TYPE
    OBJECTS { rptEvtPeriod, rptEvtValue, rptEvtVldty, rptEvtDateTime, rptEvtObjType, rptEvtParaLen, rptEvtPara}
    STATUS current
    DESCRIPTION
    "Trap of PerEvt: Average total input optical power of the L-band."
    ::= { optixTrapsPER 16538 }

--  1.3.6.1.4.1.2011.2.25.3.40.40.30.16539
    perEvtLsumoopmax NOTIFICATION-TYPE
    OBJECTS { rptEvtPeriod, rptEvtValue, rptEvtVldty, rptEvtDateTime, rptEvtObjType, rptEvtParaLen, rptEvtPara}
    STATUS current
    DESCRIPTION
    "Trap of PerEvt: Maximum total output optical power of the L-band."
    ::= { optixTrapsPER 16539 }

--  1.3.6.1.4.1.2011.2.25.3.40.40.30.16540
    perEvtLsumoopmin NOTIFICATION-TYPE
    OBJECTS { rptEvtPeriod, rptEvtValue, rptEvtVldty, rptEvtDateTime, rptEvtObjType, rptEvtParaLen, rptEvtPara}
    STATUS current
    DESCRIPTION
    "Trap of PerEvt: Minimum total output optical power of the L-band."
    ::= { optixTrapsPER 16540 }

--  1.3.6.1.4.1.2011.2.25.3.40.40.30.16541
    perEvtLsumoopcur NOTIFICATION-TYPE
    OBJECTS { rptEvtPeriod, rptEvtValue, rptEvtVldty, rptEvtDateTime, rptEvtObjType, rptEvtParaLen, rptEvtPara}
    STATUS current
    DESCRIPTION
    "Trap of PerEvt: Current total output optical power of the L-band."
    ::= { optixTrapsPER 16541 }

--  1.3.6.1.4.1.2011.2.25.3.40.40.30.16542
    perEvtLsumoopavg NOTIFICATION-TYPE
    OBJECTS { rptEvtPeriod, rptEvtValue, rptEvtVldty, rptEvtDateTime, rptEvtObjType, rptEvtParaLen, rptEvtPara}
    STATUS current
    DESCRIPTION
    "Trap of PerEvt: Average total output optical power of the L-band."
    ::= { optixTrapsPER 16542 }

    END
--
-- OPTIX-SONET-DataPm-MIB.mib
--
