-- OPTIX-OID-MIB.mib
-- Basic OID definitions for Huawei OptiX products
-- This file provides the fundamental OID definitions that other MIBs depend on

OPTIX-OID-MIB DEFINITIONS ::= BEGIN

IMPORTS
    enterprises
        FROM SNMPv2-SMI;

-- Node definitions

-- 1.3.6.1.4.1.2011
huawei OBJECT IDENTIFIER ::= { enterprises 2011 }

-- 1.3.6.1.4.1.2011.2
products OBJECT IDENTIFIER ::= { huawei 2 }

-- 1.3.6.1.4.1.2011.2.25
transmission OBJECT IDENTIFIER ::= { products 25 }

-- 1.3.6.1.4.1.2011.2.25.3
optixCommon OBJECT IDENTIFIER ::= { transmission 3 }

-- 1.3.6.1.4.1.2011.2.25.3.1
optixCommonSnmp OBJECT IDENTIFIER ::= { optixCommon 1 }

-- 1.3.6.1.4.1.2011.2.25.3.40
optixCommonGlobal OBJECT IDENTIFIER ::= { optixCommon 40 }

-- 1.3.6.1.4.1.2011.2.25.3.80
--mstp OBJECT IDENTIFIER ::= { optixCommon 80 }

-- 1.3.6.1.4.1.2011.2.25.4
optixProvision OBJECT IDENTIFIER ::= { transmission 4 }

-- 1.3.6.1.4.1.2011.2.25.4.70
optixProvisionWDM OBJECT IDENTIFIER ::= { optixProvision 70 }

END
