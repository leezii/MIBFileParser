-- OPTIX-GLOBAL-SNMP-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-GLOBAL-SNMP-MIB DEFINITIONS ::= BEGIN
    IMPORTS
        optixCommonGlobal
            FROM OPTIX-OID-MIB
        IpAddress,MODULE-IDENTITY,OBJECT-TYPE
            FROM SNMPv2-SMI
        ;

    optixGlobalSnmp MODULE-IDENTITY
        LAST-UPDATED "201208091457Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "SNMP management module"
        REVISION "201208091457Z"
        DESCRIPTION
            "The initial version"
        ::={ optixCommonGlobal 1 }

    -- 1.3.6.1.4.1.2011.2.25.3.40.1.1
    optixSnmpTrapCtrl OBJECT IDENTIFIER ::= { optixGlobalSnmp 1 }

    -- 1.3.6.1.4.1.2011.2.25.3.40.1.1.1
    optixSnmpTrapCtrlTable OBJECT-TYPE
        SYNTAX SEQUENCE OF OptixSnmpTrapCtrlEntry
        MAX-ACCESS not-accessible
        STATUS current
        DESCRIPTION
            "Indicates the table for setting the SNMP TRAP status."
        ::= { optixSnmpTrapCtrl 1 }

    -- 1.3.6.1.4.1.2011.2.25.3.40.1.1.1.1
    optixSnmpTrapCtrlEntry OBJECT-TYPE
        SYNTAX OptixSnmpTrapCtrlEntry
        MAX-ACCESS not-accessible
        STATUS current
        DESCRIPTION
            "Indicates the Entry nodes of the table for setting the SNMP TRAP status."
        INDEX{ optixTrapOid,optixIp }
        ::= { optixSnmpTrapCtrlTable 1 }

    OptixSnmpTrapCtrlEntry ::=
        SEQUENCE {
            optixTrapOid
                OBJECT IDENTIFIER,
            optixIp
                IpAddress,
            optixState
                INTEGER
        }

    -- 1.3.6.1.4.1.2011.2.25.3.40.1.1.1.1.1
    optixTrapOid OBJECT-TYPE
        SYNTAX OBJECT IDENTIFIER
        MAX-ACCESS not-accessible
        STATUS current
        DESCRIPTION
            "Indicates the TRAP OID, which is an index to the table for setting the SNMP TRAP status."
        ::= { optixSnmpTrapCtrlEntry 1 }

    -- 1.3.6.1.4.1.2011.2.25.3.40.1.1.1.1.2
    optixIp OBJECT-TYPE
        SYNTAX IpAddress
        MAX-ACCESS not-accessible
        STATUS current
        DESCRIPTION
            "Indicates the IP address, which is an index to the table for setting the SNMP TRAP status."
        ::= { optixSnmpTrapCtrlEntry 2 }

    -- 1.3.6.1.4.1.2011.2.25.3.40.1.1.1.1.3
    optixState OBJECT-TYPE
        SYNTAX INTEGER
        {
            disable(0),
            enable(1)
        }
        MAX-ACCESS read-write
        STATUS current
        DESCRIPTION
            "Indicates the SNMP TRAP status: enable/disable."
        ::= { optixSnmpTrapCtrlEntry 3 }

END
