-- =================================================================
--  Copyright (C) 2006 by HUAWEI TECHNOLOGIES. All rights reserved
--  
--  Description:This MIB describes the Data		pmformance interface of Huawei macrowave transmit
--  Reference:
--  Version: V1.00
--  History:
-- 	<author>,<date>,<contents>
-- =================================================================
-- 

	OPTIX-GLOBAL-PM-TRAPS-MSTP-MIB DEFINITIONS ::= BEGIN
 
		IMPORTS
			optixGlobalTrap,  rptEvtPeriod, rptEvtValue, rptEvtVldty, 
			rptEvtDateTime, rptEvtObjType,rptEvtParaLen, rptEvtPara			
				FROM OPTIX-GLOBAL-TRAPS-MIB			
			NOTIFICATION-TYPE			
				FROM SNMPv2-SMI;
	
--
-- Node definitions
--	
		-- 1.3.6.1.4.1.2011.2.25.3.40.40.20
		optixTrapsPM OBJECT IDENTIFIER ::= { optixGlobalTrap 20 }

		pmRXPKT64 NOTIFICATION-TYPE
			OBJECTS{ rptEvtPeriod, rptEvtValue, rptEvtVldty, rptEvtDateTime, rptEvtObjType,
				rptEvtParaLen, rptEvtPara}
			STATUS current
			DESCRIPTION
				"The total number of received packets (including bad packets) whose length is 64 bytes (excluding framing bits, but including FCS bytes)."
			::= { optixTrapsPM  101}

		pmRXPKT65 NOTIFICATION-TYPE
			OBJECTS{ rptEvtPeriod, rptEvtValue, rptEvtVldty, rptEvtDateTime, rptEvtObjType,
				rptEvtParaLen, rptEvtPara}
			STATUS current
			DESCRIPTION
				"The total number of received packets (including bad packets) whose length is between 65 and 127 bytes (excluding framing bits, but including FCS bytes)."
			::= { optixTrapsPM  102}
    
		pmRXPKT128 NOTIFICATION-TYPE
			OBJECTS{ rptEvtPeriod, rptEvtValue, rptEvtVldty, rptEvtDateTime, rptEvtObjType,
				rptEvtParaLen, rptEvtPara}
			STATUS current
			DESCRIPTION
				"The total number of received packets (including bad packets) whose length is between 128 and 255 bytes (excluding framing bits, but including FCS bytes)."
			::= { optixTrapsPM  103}
    
		pmRXPKT256 NOTIFICATION-TYPE
			OBJECTS{ rptEvtPeriod, rptEvtValue, rptEvtVldty, rptEvtDateTime, rptEvtObjType,
				rptEvtParaLen, rptEvtPara}
			STATUS current
			DESCRIPTION
				"The total number of received packets (including bad packets) whose length is between 256 and 511 bytes (excluding framing bits, but including FCS bytes)."
			::= { optixTrapsPM  104}
    
		pmRXPKT512 NOTIFICATION-TYPE
			OBJECTS{ rptEvtPeriod, rptEvtValue, rptEvtVldty, rptEvtDateTime, rptEvtObjType,
				rptEvtParaLen, rptEvtPara}
			STATUS current
			DESCRIPTION
				"The total number of received packets (including bad packets) whose length is between 512 and 1023 bytes (excluding framing bits, but including FCS bytes)."
			::= { optixTrapsPM  105}
    
		pmRXPKT1024 NOTIFICATION-TYPE
			OBJECTS{ rptEvtPeriod, rptEvtValue, rptEvtVldty, rptEvtDateTime, rptEvtObjType,
				rptEvtParaLen, rptEvtPara}
			STATUS current
			DESCRIPTION
				"The total number of received packets (including bad packets) whose length is between 1024 and 1518 bytes (excluding framing bits, but including FCS bytes)."
			::= { optixTrapsPM  106}
    
		pmTXPKT64 NOTIFICATION-TYPE
			OBJECTS{ rptEvtPeriod, rptEvtValue, rptEvtVldty, rptEvtDateTime, rptEvtObjType,
				rptEvtParaLen, rptEvtPara}
			STATUS current
			DESCRIPTION
				"The total number of transmitted packets (including bad packets) whose length is between 64 bytes (excluding framing bits, but including FCS bytes)."
			::= { optixTrapsPM  107}
    
		pmTXPKT65 NOTIFICATION-TYPE
			OBJECTS{ rptEvtPeriod, rptEvtValue, rptEvtVldty, rptEvtDateTime, rptEvtObjType,
				rptEvtParaLen, rptEvtPara}
			STATUS current
			DESCRIPTION
				"The total number of transmitted packets (including bad packets) whose length is between 65 and 127 bytes (excluding framing bits, but including FCS bytes)."
			::= { optixTrapsPM  108}
    
		pmTXPKT128 NOTIFICATION-TYPE
			OBJECTS{ rptEvtPeriod, rptEvtValue, rptEvtVldty, rptEvtDateTime, rptEvtObjType,
				rptEvtParaLen, rptEvtPara}
			STATUS current
			DESCRIPTION
				"The total number of transmitted packets (including bad packets) whose length is between 128 and 255 bytes (excluding framing bits, but including FCS bytes)."
			::= { optixTrapsPM  109} 
    
		pmTXPKT256 NOTIFICATION-TYPE
			OBJECTS{ rptEvtPeriod, rptEvtValue, rptEvtVldty, rptEvtDateTime, rptEvtObjType,
				rptEvtParaLen, rptEvtPara}
			STATUS current
			DESCRIPTION
				"The total number of transmitted packets (including bad packets) whose length is between 256 and 511 bytes (excluding framing bits, but including FCS bytes)."
			::= { optixTrapsPM  110}    

		pmTXPKT512 NOTIFICATION-TYPE
			OBJECTS{ rptEvtPeriod, rptEvtValue, rptEvtVldty, rptEvtDateTime, rptEvtObjType,
				rptEvtParaLen, rptEvtPara}
			STATUS current
			DESCRIPTION
				"The total number of transmitted packets (including bad packets) whose length is between 512 and 1023 bytes (excluding framing bits, but including FCS bytes)."
			::= { optixTrapsPM  111}

		pmTXPKT1024 NOTIFICATION-TYPE
			OBJECTS{ rptEvtPeriod, rptEvtValue, rptEvtVldty, rptEvtDateTime, rptEvtObjType,
				rptEvtParaLen, rptEvtPara}
			STATUS current
			DESCRIPTION
				"The total number of transmitted packets (including bad packets) whose length is between 1024 and 1518 bytes (excluding framing bits, but including FCS bytes)."
			::= { optixTrapsPM  112}

		pmRXUNICAST NOTIFICATION-TYPE
			OBJECTS{ rptEvtPeriod, rptEvtValue, rptEvtVldty, rptEvtDateTime, rptEvtObjType,
				rptEvtParaLen, rptEvtPara}
			STATUS current
			DESCRIPTION
				"The total number of unicast good packets received."
			::= { optixTrapsPM  113}

		pmRXMULCAST NOTIFICATION-TYPE
			OBJECTS{ rptEvtPeriod, rptEvtValue, rptEvtVldty, rptEvtDateTime, rptEvtObjType,
				rptEvtParaLen, rptEvtPara}
			STATUS current
			DESCRIPTION
				"The total number of received good packets (excluding broadcast packets) whose destination address is a multicast address."
			::= { optixTrapsPM  114}

		pmRXBRDCAST NOTIFICATION-TYPE
			OBJECTS{ rptEvtPeriod, rptEvtValue, rptEvtVldty, rptEvtDateTime, rptEvtObjType,
				rptEvtParaLen, rptEvtPara}
			STATUS current
			DESCRIPTION
				"The total number of received good packets (excluding multicast packets) whose destination address is the broadcast address."
			::= { optixTrapsPM  115}
    
		pmTXUNICAST NOTIFICATION-TYPE
			OBJECTS{ rptEvtPeriod, rptEvtValue, rptEvtVldty, rptEvtDateTime, rptEvtObjType,
				rptEvtParaLen, rptEvtPara}
			STATUS current
			DESCRIPTION
				"The total number of transmitted unicast packets, including packets that are discarded and are not successfully transmitted."
			::= { optixTrapsPM  116}

		pmTXMULCAST NOTIFICATION-TYPE
			OBJECTS{ rptEvtPeriod, rptEvtValue, rptEvtVldty, rptEvtDateTime, rptEvtObjType,
				rptEvtParaLen, rptEvtPara}
			STATUS current
			DESCRIPTION
				"The total number of transmitted multicast packets, including packets that are discarded and are not successfully transmitted."
			::= { optixTrapsPM  117}
    
		pmTXBRDCAST NOTIFICATION-TYPE
			OBJECTS{ rptEvtPeriod, rptEvtValue, rptEvtVldty, rptEvtDateTime, rptEvtObjType,
				rptEvtParaLen, rptEvtPara}
			STATUS current
			DESCRIPTION
				"The total number of transmitted broadcast packets, including packets that are discarded and are not successfully transmitted."
			::= { optixTrapsPM  118}
    
		pmRXPAUSE NOTIFICATION-TYPE
			OBJECTS{ rptEvtPeriod, rptEvtValue, rptEvtVldty, rptEvtDateTime, rptEvtObjType,
				rptEvtParaLen, rptEvtPara}
			STATUS current
			DESCRIPTION
				"A count of received MAC flow control frames that have the PAUSE operation code."
			::= { optixTrapsPM  119}
    
		pmTXPAUSE NOTIFICATION-TYPE
			OBJECTS{ rptEvtPeriod, rptEvtValue, rptEvtVldty, rptEvtDateTime, rptEvtObjType,
				rptEvtParaLen, rptEvtPara}
			STATUS current
			DESCRIPTION
				"A count of transmitted MAC flow control frames that have the PAUSE operation code."
			::= { optixTrapsPM  120}

		pmETHUNDER NOTIFICATION-TYPE
			OBJECTS{ rptEvtPeriod, rptEvtValue, rptEvtVldty, rptEvtDateTime, rptEvtObjType,
				rptEvtParaLen, rptEvtPara}
			STATUS current
			DESCRIPTION
				"The total number of received packets (excluding framing bits, but including FCS bytes) that have a length of smaller than 64 bytes, and that do not have any other errors."
			::= { optixTrapsPM  122}
    
		pmETHOVER NOTIFICATION-TYPE
			OBJECTS{ rptEvtPeriod, rptEvtValue, rptEvtVldty, rptEvtDateTime, rptEvtObjType,
				rptEvtParaLen, rptEvtPara}
			STATUS current
			DESCRIPTION
				"The total number of received packets (excluding framing bits, but including FCS bytes) that have a length of greater than 1518 bytes, and that do not have any other errors."
			::= { optixTrapsPM  123}
  
		pmETHFRG NOTIFICATION-TYPE
			OBJECTS{ rptEvtPeriod, rptEvtValue, rptEvtVldty, rptEvtDateTime, rptEvtObjType,
				rptEvtParaLen, rptEvtPara}
			STATUS current
			DESCRIPTION
				"The total number of received packets (excluding framing bits, but including FCS bytes) that have a length of smaller than 64 bytes, and that have FCS errors or alignment errors. Due to the existence of noise collision, the increase of this number is normal."
			::= { optixTrapsPM  124}    
    
		pmETHJAB NOTIFICATION-TYPE
			OBJECTS{ rptEvtPeriod, rptEvtValue, rptEvtVldty, rptEvtDateTime, rptEvtObjType,
				rptEvtParaLen, rptEvtPara}
			STATUS current
			DESCRIPTION
				"The total number of received packets (excluding framing bits, but including FCS bytes) that have a length of greater than 1518 bytes, and that have FCS errors or alignment errors."
			::= { optixTrapsPM  125}
    
		pmRXBGOOD NOTIFICATION-TYPE
			OBJECTS{ rptEvtPeriod, rptEvtValue, rptEvtVldty, rptEvtDateTime, rptEvtObjType,
				rptEvtParaLen, rptEvtPara}
			STATUS current
			DESCRIPTION
				"The total number of octets of good packets received on the network (excluding framing bits but including FCS octets)."
			::= { optixTrapsPM  126}  
    
		pmTXBGOOD NOTIFICATION-TYPE
			OBJECTS{ rptEvtPeriod, rptEvtValue, rptEvtVldty, rptEvtDateTime, rptEvtObjType,
				rptEvtParaLen, rptEvtPara}
			STATUS current
			DESCRIPTION
				"The total number of octets of good packets transmitted on the network (excluding framing bits but including FCS octets)."
			::= { optixTrapsPM  127}  
    
		pmRXBBAD NOTIFICATION-TYPE
			OBJECTS{ rptEvtPeriod, rptEvtValue, rptEvtVldty, rptEvtDateTime, rptEvtObjType,
				rptEvtParaLen, rptEvtPara}
			STATUS current
			DESCRIPTION
				"The total number of received bad-packet bytes (excluding framing bits, but including FCS bytes)."
			::= { optixTrapsPM  128}  
		
		pmTXBBAD NOTIFICATION-TYPE
			OBJECTS{ rptEvtPeriod, rptEvtValue, rptEvtVldty, rptEvtDateTime, rptEvtObjType,
				rptEvtParaLen, rptEvtPara}
			STATUS current
			DESCRIPTION
				"The total number of transmitted bad-packet bytes (excluding framing bits, but including FCS bytes)."
			::= { optixTrapsPM  129}

		pmETHFCS NOTIFICATION-TYPE
			OBJECTS{ rptEvtPeriod, rptEvtValue, rptEvtVldty, rptEvtDateTime, rptEvtObjType,
				rptEvtParaLen, rptEvtPara}
			STATUS current
			DESCRIPTION
				"A count of received frames that are an integer number of bytes in length and have FCS errors. This count does not include oversize and undersize frames."
			::= { optixTrapsPM  132}

        pmRXPKT1519 NOTIFICATION-TYPE
			OBJECTS{ rptEvtPeriod, rptEvtValue, rptEvtVldty, rptEvtDateTime, rptEvtObjType,
				rptEvtParaLen, rptEvtPara}
			STATUS current
			DESCRIPTION
				"The number of receive packets,with lengths between 1519 bytes and the maximum packet size,including bad packets."
			::= { optixTrapsPM  139}
		
		pmTXPKT1519 NOTIFICATION-TYPE
			OBJECTS{ rptEvtPeriod, rptEvtValue, rptEvtVldty, rptEvtDateTime, rptEvtObjType,
				rptEvtParaLen, rptEvtPara}
			STATUS current
			DESCRIPTION
				"The Number Of Transmitted Packets Larger than 1518 Bytes, Including Bad Packets."
			::= { optixTrapsPM  140}

--  1.3.6.1.4.1.2011.2.25.3.40.40.20.147

		pmRXCTLPKTS NOTIFICATION-TYPE
			OBJECTS{ rptEvtPeriod, rptEvtValue, rptEvtVldty, rptEvtDateTime, rptEvtObjType,
				rptEvtParaLen, rptEvtPara}
			STATUS current
			DESCRIPTION
				"A count of received control frames"
			::= { optixTrapsPM  194}
    
		pmTXCTLPKTS NOTIFICATION-TYPE
			OBJECTS{ rptEvtPeriod, rptEvtValue, rptEvtVldty, rptEvtDateTime, rptEvtObjType,
				rptEvtParaLen, rptEvtPara}
			STATUS current
			DESCRIPTION
				"A count of transmitted control frames"
			::= { optixTrapsPM  195}

		pmTXETHOVER NOTIFICATION-TYPE
			OBJECTS{ rptEvtPeriod, rptEvtValue, rptEvtVldty, rptEvtDateTime, rptEvtObjType,
				rptEvtParaLen, rptEvtPara}
			STATUS current
			DESCRIPTION
				"Oversize packets transmitted."
			::= { optixTrapsPM  197}
    
		pmTXPKTS NOTIFICATION-TYPE
			OBJECTS{ rptEvtPeriod, rptEvtValue, rptEvtVldty, rptEvtDateTime, rptEvtObjType,
				rptEvtParaLen, rptEvtPara}
			STATUS current
			DESCRIPTION
				"The total number of transmitted packets (including bad packets, broadcast packets, and multicast packets)."
			::= { optixTrapsPM  198}
    
		pmTXOCTETS NOTIFICATION-TYPE
			OBJECTS{ rptEvtPeriod, rptEvtValue, rptEvtVldty, rptEvtDateTime, rptEvtObjType,
				rptEvtParaLen, rptEvtPara}
			STATUS current
			DESCRIPTION
				"The total number of transmitted bytes (including bad-packet bytes and FCS bytes, and excluding framing bits)."
			::= { optixTrapsPM  199}

		pmRXOCTETS NOTIFICATION-TYPE
			OBJECTS{ rptEvtPeriod, rptEvtValue, rptEvtVldty, rptEvtDateTime, rptEvtObjType,
				rptEvtParaLen, rptEvtPara}
			STATUS current
			DESCRIPTION
				"The total number of received bytes (including bad-packet bytes and FCS bytes, and excluding framing bits)."
			::= { optixTrapsPM  200}
    
		pmRXPKTS NOTIFICATION-TYPE
			OBJECTS{ rptEvtPeriod, rptEvtValue, rptEvtVldty, rptEvtDateTime, rptEvtObjType,
				rptEvtParaLen, rptEvtPara}
			STATUS current
			DESCRIPTION
				"The total number of received packets (including bad packets, broadcast packets, and multicast packets)."
			::= { optixTrapsPM  201}

	--  1.3.6.1.4.1.2011.2.25.3.40.40.20.203

	--  1.3.6.1.4.1.2011.2.25.3.40.40.20.303

	--  1.3.6.1.4.1.2011.2.25.3.40.40.20.304

	--  1.3.6.1.4.1.2011.2.25.3.40.40.20.305

	--  1.3.6.1.4.1.2011.2.25.3.40.40.20.306

	--  1.3.6.1.4.1.2011.2.25.3.40.40.20.307

	--  1.3.6.1.4.1.2011.2.25.3.40.40.20.308

	--  1.3.6.1.4.1.2011.2.25.3.40.40.20.309

	--  1.3.6.1.4.1.2011.2.25.3.40.40.20.310

	--  1.3.6.1.4.1.2011.2.25.3.40.40.20.311

	--  1.3.6.1.4.1.2011.2.25.3.40.40.20.312

	--  1.3.6.1.4.1.2011.2.25.3.40.40.20.313

	--  1.3.6.1.4.1.2011.2.25.3.40.40.20.314

	--  1.3.6.1.4.1.2011.2.25.3.40.40.20.315

	--  1.3.6.1.4.1.2011.2.25.3.40.40.20.316

	--  1.3.6.1.4.1.2011.2.25.3.40.40.20.317

	--  1.3.6.1.4.1.2011.2.25.3.40.40.20.318

	--  1.3.6.1.4.1.2011.2.25.3.40.40.20.319

	--  1.3.6.1.4.1.2011.2.25.3.40.40.20.321

	--  1.3.6.1.4.1.2011.2.25.3.40.40.20.322

	--  1.3.6.1.4.1.2011.2.25.3.40.40.20.323

	--  1.3.6.1.4.1.2011.2.25.3.40.40.20.325

	--  1.3.6.1.4.1.2011.2.25.3.40.40.20.326

	--  1.3.6.1.4.1.2011.2.25.3.40.40.20.327

	--  1.3.6.1.4.1.2011.2.25.3.40.40.20.328

	--  1.3.6.1.4.1.2011.2.25.3.40.40.20.329

	--  1.3.6.1.4.1.2011.2.25.3.40.40.20.330

	--  1.3.6.1.4.1.2011.2.25.3.40.40.20.331

	--  1.3.6.1.4.1.2011.2.25.3.40.40.20.332

	--  1.3.6.1.4.1.2011.2.25.3.40.40.20.333

	--  1.3.6.1.4.1.2011.2.25.3.40.40.20.336

	--  1.3.6.1.4.1.2011.2.25.3.40.40.20.337

	--  1.3.6.1.4.1.2011.2.25.3.40.40.20.338

	--  1.3.6.1.4.1.2011.2.25.3.40.40.20.340

	--  1.3.6.1.4.1.2011.2.25.3.40.40.20.341

	--  1.3.6.1.4.1.2011.2.25.3.40.40.20.342

	--  1.3.6.1.4.1.2011.2.25.3.40.40.20.344

	--  1.3.6.1.4.1.2011.2.25.3.40.40.20.345

	--  1.3.6.1.4.1.2011.2.25.3.40.40.20.346

	--  1.3.6.1.4.1.2011.2.25.3.40.40.20.347

	--  1.3.6.1.4.1.2011.2.25.3.40.40.20.348

	--  1.3.6.1.4.1.2011.2.25.3.40.40.20.349

--  1.3.6.1.4.1.2011.2.25.3.40.40.20.401

--  1.3.6.1.4.1.2011.2.25.3.40.40.20.402

--  1.3.6.1.4.1.2011.2.25.3.40.40.20.403

--  1.3.6.1.4.1.2011.2.25.3.40.40.20.505

               	pmPORTRXBWUTILIZATION NOTIFICATION-TYPE                                                                    
               		OBJECTS { rptEvtPeriod, rptEvtValue, rptEvtVldty, rptEvtDateTime, rptEvtObjType, rptEvtParaLen, rptEvtPara}
               		STATUS current                                                                                             
               		DESCRIPTION                                                                                                
               		    "The bandwidth utilization of the received port"                                                     
               		::= { optixTrapsPM  567}                                                                                  
               	                                                                                                           
               	pmPORTTXBWUTILIZATION NOTIFICATION-TYPE                                                                    
               		OBJECTS { rptEvtPeriod, rptEvtValue, rptEvtVldty, rptEvtDateTime, rptEvtObjType, rptEvtParaLen, rptEvtPara}
               		STATUS current                                                                                             
               		DESCRIPTION                                                                                                
               		    "The bandwidth utilization of the transmitted port"                                                  
               		::= { optixTrapsPM  568}      
     
	--  1.3.6.1.4.1.2011.2.25.3.40.40.20.577

        pmPORTRXBWUTILIZATIONMIN NOTIFICATION-TYPE                                                                    
	 	    	OBJECTS { rptEvtPeriod, rptEvtValue, rptEvtVldty, rptEvtDateTime, rptEvtObjType, rptEvtParaLen, rptEvtPara}
	 	    	STATUS current                                                                                             
	 	    	DESCRIPTION                                                                                                
	 	    	    	"Minimum bandwidth utilization of the receive port."                                                 
	       	    	::= { optixTrapsPM  839}
					
		pmPORTRXBWUTILIZATIONAVG NOTIFICATION-TYPE                                                                    
	 	    	OBJECTS { rptEvtPeriod, rptEvtValue, rptEvtVldty, rptEvtDateTime, rptEvtObjType, rptEvtParaLen, rptEvtPara}
	 	    	STATUS current                                                                                             
	 	    	DESCRIPTION                                                                                                
	 	    	    	"Average bandwidth utilization of the receive port."                                                 
	       	    	::= { optixTrapsPM  840}
		pmPORTRXBWUTILIZATIONMAX NOTIFICATION-TYPE                                                                    
	 	    	OBJECTS { rptEvtPeriod, rptEvtValue, rptEvtVldty, rptEvtDateTime, rptEvtObjType, rptEvtParaLen, rptEvtPara}
	 	    	STATUS current                                                                                             
	 	    	DESCRIPTION                                                                                                
	 	    	    	"Maximum bandwidth utilization of the receive port."                                                 
	       	    	::= { optixTrapsPM  841}
		pmPORTTXBWUTILIZATIONMIN NOTIFICATION-TYPE                                                                    
	 	    	OBJECTS { rptEvtPeriod, rptEvtValue, rptEvtVldty, rptEvtDateTime, rptEvtObjType, rptEvtParaLen, rptEvtPara}
	 	    	STATUS current                                                                                             
	 	    	DESCRIPTION                                                                                                
	 	    	    	"Minimum bandwidth utilization of the transmit port."                                                 
	       	    	::= { optixTrapsPM  842}
		pmPORTTXBWUTILIZATIONAVG NOTIFICATION-TYPE                                                                    
	 	    	OBJECTS { rptEvtPeriod, rptEvtValue, rptEvtVldty, rptEvtDateTime, rptEvtObjType, rptEvtParaLen, rptEvtPara}
	 	    	STATUS current                                                                                             
	 	    	DESCRIPTION                                                                                                
	 	    	    	"Average bandwidth utilization of the transmit port."                                                 
	       	    	::= { optixTrapsPM  843}
		pmPORTTXBWUTILIZATIONMAX NOTIFICATION-TYPE                                                                    
	 	    	OBJECTS { rptEvtPeriod, rptEvtValue, rptEvtVldty, rptEvtDateTime, rptEvtObjType, rptEvtParaLen, rptEvtPara}
	 	    	STATUS current                                                                                             
	 	    	DESCRIPTION                                                                                                
	 	    	    	"Maximum bandwidth utilization of the transmit port."                                                 
	       	    	::= { optixTrapsPM  844}
	    pmRXPBAD NOTIFICATION-TYPE
			OBJECTS{ rptEvtPeriod,rptEvtValue,rptEvtVldty,rptEvtDateTime,rptEvtObjType,rptEvtParaLen,rptEvtPara }
			STATUS current
			DESCRIPTION
				"Bad packets received."
			::= { optixTrapsPM 944 }
		pmTXPBAD NOTIFICATION-TYPE
			OBJECTS{ rptEvtPeriod,rptEvtValue,rptEvtVldty,rptEvtDateTime,rptEvtObjType,rptEvtParaLen,rptEvtPara }
			STATUS current
			DESCRIPTION
				"Bad packets transmitted."
			::= { optixTrapsPM 945 }    	
 		pmRXPGOOD NOTIFICATION-TYPE                                                                    
	 	    	OBJECTS { rptEvtPeriod, rptEvtValue, rptEvtVldty, rptEvtDateTime, rptEvtObjType, rptEvtParaLen, rptEvtPara}
	 	    	STATUS current                                                                                             
	 	    	DESCRIPTION                                                                                                
	 	    	    	"Good packets received."                                                 
	       	    	::= { optixTrapsPM  946}
		pmTXPGOOD NOTIFICATION-TYPE                                                                    
	 	    	OBJECTS { rptEvtPeriod, rptEvtValue, rptEvtVldty, rptEvtDateTime, rptEvtObjType, rptEvtParaLen, rptEvtPara}
	 	    	STATUS current                                                                                             
	 	    	DESCRIPTION                                                                                                
	 	    	    	"Good packets transmitted."                                                 
	       	    	::= { optixTrapsPM  947}  


--  1.3.6.1.4.1.2011.2.25.3.40.40.20.121
    pmETHDROP NOTIFICATION-TYPE
        OBJECTS { rptEvtPeriod, rptEvtValue, rptEvtVldty, rptEvtDateTime, rptEvtObjType, rptEvtParaLen, rptEvtPara}
        STATUS current
        DESCRIPTION
            "The total number of events in which packets were dropped by the probe due to lack of resources"
             ::= { optixTrapsPM  121}
			 








--  1.3.6.1.4.1.2011.2.25.3.40.40.20.131
    pmETHALI NOTIFICATION-TYPE
        OBJECTS { rptEvtPeriod, rptEvtValue, rptEvtVldty, rptEvtDateTime, rptEvtObjType, rptEvtParaLen, rptEvtPara}
        STATUS current
        DESCRIPTION
            "A count of frames received on a particular interface that are not an integral number of octets in length and do not pass the FCS check"
             ::= { optixTrapsPM  131}

--  1.3.6.1.4.1.2011.2.25.3.40.40.20.190
    pmRXGOODFULLFRAMESPEED NOTIFICATION-TYPE
        OBJECTS { rptEvtPeriod, rptEvtValue, rptEvtVldty, rptEvtDateTime, rptEvtObjType, rptEvtParaLen, rptEvtPara}
        STATUS current
        DESCRIPTION
            "The rate of received good packets, including framing bits (20 bytes) and FCS bytes"
             ::= { optixTrapsPM  190}

--  1.3.6.1.4.1.2011.2.25.3.40.40.20.191
    pmTXGOODFULLFRAMESPEED NOTIFICATION-TYPE
        OBJECTS { rptEvtPeriod, rptEvtValue, rptEvtVldty, rptEvtDateTime, rptEvtObjType, rptEvtParaLen, rptEvtPara}
        STATUS current
        DESCRIPTION
            "The rate of transmitted good packets, including framing bits (20 bytes) and FCS bytes"
             ::= { optixTrapsPM  191}

--  1.3.6.1.4.1.2011.2.25.3.40.40.20.196
    pmTXETHDROP NOTIFICATION-TYPE
        OBJECTS { rptEvtPeriod, rptEvtValue, rptEvtVldty, rptEvtDateTime, rptEvtObjType, rptEvtParaLen, rptEvtPara}
        STATUS current
        DESCRIPTION
            "The total number of events in which packets were dropped by the probe due to lack of resources at transmission direction"
             ::= { optixTrapsPM  196}   
             
            -- 1.3.6.1.4.1.2011.2.25.3.40.40.20.141
    pmPKT64 NOTIFICATION-TYPE
        OBJECTS { rptEvtPeriod, rptEvtValue, rptEvtVldty, rptEvtDateTime, rptEvtObjType, rptEvtParaLen, rptEvtPara}
        STATUS current
        DESCRIPTION
            "Packets received and transmitted (64 bytes in length)."
             ::= { optixTrapsPM 141 }

-- 1.3.6.1.4.1.2011.2.25.3.40.40.20.142
    pmPKT65        NOTIFICATION-TYPE
        OBJECTS { rptEvtPeriod, rptEvtValue, rptEvtVldty, rptEvtDateTime, rptEvtObjType, rptEvtParaLen, rptEvtPara}
        STATUS current
        DESCRIPTION
            "Packets received and transmitted (65-127 bytes in length)."
             ::= { optixTrapsPM 142 }

-- 1.3.6.1.4.1.2011.2.25.3.40.40.20.143
    pmPKT128       NOTIFICATION-TYPE
        OBJECTS { rptEvtPeriod, rptEvtValue, rptEvtVldty, rptEvtDateTime, rptEvtObjType, rptEvtParaLen, rptEvtPara}
        STATUS current
        DESCRIPTION
            "Packets received and transmitted (128-255 bytes in length)."
             ::= { optixTrapsPM 143 }

-- 1.3.6.1.4.1.2011.2.25.3.40.40.20.144
    pmPKT256       NOTIFICATION-TYPE
        OBJECTS { rptEvtPeriod, rptEvtValue, rptEvtVldty, rptEvtDateTime, rptEvtObjType, rptEvtParaLen, rptEvtPara}
        STATUS current
        DESCRIPTION
            "Packets received and transmitted (256-511 bytes in length)."
             ::= { optixTrapsPM 144 }

-- 1.3.6.1.4.1.2011.2.25.3.40.40.20.145
    pmPKT512       NOTIFICATION-TYPE
        OBJECTS { rptEvtPeriod, rptEvtValue, rptEvtVldty, rptEvtDateTime, rptEvtObjType, rptEvtParaLen, rptEvtPara}
        STATUS current
        DESCRIPTION
            "Packets received and transmitted (512-1023 bytes in length)."
             ::= { optixTrapsPM 145 }

-- 1.3.6.1.4.1.2011.2.25.3.40.40.20.146
    pmPKT1024      NOTIFICATION-TYPE
        OBJECTS { rptEvtPeriod, rptEvtValue, rptEvtVldty, rptEvtDateTime, rptEvtObjType, rptEvtParaLen, rptEvtPara}
        STATUS current
        DESCRIPTION
            "Packets received and transmitted (1024-1518 bytes in length)."
             ::= { optixTrapsPM 146 }

-- 1.3.6.1.4.1.2011.2.25.3.40.40.20.147
    pmPKT1519      NOTIFICATION-TYPE
        OBJECTS { rptEvtPeriod, rptEvtValue, rptEvtVldty, rptEvtDateTime, rptEvtObjType, rptEvtParaLen, rptEvtPara}
        STATUS current
        DESCRIPTION
            "Packets received and transmitted (1519 bytes to the MTU in length)."
             ::= { optixTrapsPM 147 }

-- 1.3.6.1.4.1.2011.2.25.3.40.40.20.350
    pmVCGRXOCTETS NOTIFICATION-TYPE
        OBJECTS { rptEvtPeriod, rptEvtValue, rptEvtVldty, rptEvtDateTime, rptEvtObjType, rptEvtParaLen, rptEvtPara}
        STATUS current
        DESCRIPTION
            "Bytes received by ETH VCG ports."
             ::= { optixTrapsPM 350 }

-- 1.3.6.1.4.1.2011.2.25.3.40.40.20.351
    pmVCGTXOCTETS NOTIFICATION-TYPE
        OBJECTS { rptEvtPeriod, rptEvtValue, rptEvtVldty, rptEvtDateTime, rptEvtObjType, rptEvtParaLen, rptEvtPara}
        STATUS current
        DESCRIPTION
            "Bytes transmitted by ETH VCG ports."
             ::= { optixTrapsPM 351 }

-- 1.3.6.1.4.1.2011.2.25.3.40.40.20.352
    pmVCGRXPACKETS NOTIFICATION-TYPE
        OBJECTS { rptEvtPeriod, rptEvtValue, rptEvtVldty, rptEvtDateTime, rptEvtObjType, rptEvtParaLen, rptEvtPara}
        STATUS current
        DESCRIPTION
            "Packets received by ETH VCG ports."
             ::= { optixTrapsPM 352 }

-- 1.3.6.1.4.1.2011.2.25.3.40.40.20.353
    pmVCGTXPACKETS NOTIFICATION-TYPE
        OBJECTS { rptEvtPeriod, rptEvtValue, rptEvtVldty, rptEvtDateTime, rptEvtObjType, rptEvtParaLen, rptEvtPara}
        STATUS current
        DESCRIPTION
            "Packets transmitted by ETH VCG ports."
             ::= { optixTrapsPM 353 }

-- 1.3.6.1.4.1.2011.2.25.3.40.40.20.354
    pmVCGRXGOODPACKETS NOTIFICATION-TYPE
        OBJECTS { rptEvtPeriod, rptEvtValue, rptEvtVldty, rptEvtDateTime, rptEvtObjType, rptEvtParaLen, rptEvtPara}
        STATUS current
        DESCRIPTION
            "Good Packets Received."
             ::= { optixTrapsPM 354 }

-- 1.3.6.1.4.1.2011.2.25.3.40.40.20.355
    pmVCGTXGOODPACKETS NOTIFICATION-TYPE
        OBJECTS { rptEvtPeriod, rptEvtValue, rptEvtVldty, rptEvtDateTime, rptEvtObjType, rptEvtParaLen, rptEvtPara}
        STATUS current
        DESCRIPTION
            "Good Packets Transmitted."
             ::= { optixTrapsPM 355 }

-- 1.3.6.1.4.1.2011.2.25.3.40.40.20.356
    pmVCGRXSPEED NOTIFICATION-TYPE
        OBJECTS { rptEvtPeriod, rptEvtValue, rptEvtVldty, rptEvtDateTime, rptEvtObjType, rptEvtParaLen, rptEvtPara}
        STATUS current
        DESCRIPTION
            "Full Frame Speed Received."
             ::= { optixTrapsPM 356 }

-- 1.3.6.1.4.1.2011.2.25.3.40.40.20.357
    pmVCGTXSPEED NOTIFICATION-TYPE
        OBJECTS { rptEvtPeriod, rptEvtValue, rptEvtVldty, rptEvtDateTime, rptEvtObjType, rptEvtParaLen, rptEvtPara}
        STATUS current
        DESCRIPTION
            "Full Frame Speed Transmitted."
             ::= { optixTrapsPM 357 }

--  1.3.6.1.4.1.2011.2.25.3.40.40.20.192
	pmRxfullbgood NOTIFICATION-TYPE
	OBJECTS { rptEvtObjType, rptEvtParaLen, rptEvtPara, rptEvtDataPmName, rptEvtMonValue, rptEvtThValue, rptEvtDateTime}
	STATUS current
	DESCRIPTION
		"Trap of Pm: Good full-frame bytes received"
	::= { optixTrapsPM  192}
--  1.3.6.1.4.1.2011.2.25.3.40.40.20.193
	pmTxfullbgood NOTIFICATION-TYPE
	OBJECTS { rptEvtObjType, rptEvtParaLen, rptEvtPara, rptEvtDataPmName, rptEvtMonValue, rptEvtThValue, rptEvtDateTime}
	STATUS current
	DESCRIPTION
		"Trap of Pm: Good full-frame bytes transmitted"
	::= { optixTrapsPM  193}
--  1.3.6.1.4.1.2011.2.25.3.40.40.20.868
	pmPortrxbytesavailability868 NOTIFICATION-TYPE
	OBJECTS { rptEvtObjType, rptEvtParaLen, rptEvtPara, rptEvtDataPmName, rptEvtMonValue, rptEvtThValue, rptEvtDateTime}
	STATUS current
	DESCRIPTION
		"Trap of Pm: Port bandwidth availability"
	::= { optixTrapsPM  868}
--  1.3.6.1.4.1.2011.2.25.3.40.40.20.869
	pmPortrxbytesavailability869 NOTIFICATION-TYPE
	OBJECTS { rptEvtObjType, rptEvtParaLen, rptEvtPara, rptEvtDataPmName, rptEvtMonValue, rptEvtThValue, rptEvtDateTime}
	STATUS current
	DESCRIPTION
		"Trap of Pm: Port bandwidth availability"
	::= { optixTrapsPM  869}
	-- 1.3.6.1.4.1.2011.2.25.3.40.40.20.680
    pmTXBPS NOTIFICATION-TYPE
        OBJECTS{ rptEvtPeriod,rptEvtValue,rptEvtVldty,rptEvtDateTime,rptEvtObjType,rptEvtParaLen,rptEvtPara }
        STATUS current
        DESCRIPTION
            "Bits per second of transmitted ethernet port, that is, number of actually transmitted bytes x 8/time unit."
        ::= { optixTrapsPM 680 }

    -- 1.3.6.1.4.1.2011.2.25.3.40.40.20.682
    pmTXPPS NOTIFICATION-TYPE
        OBJECTS{ rptEvtPeriod,rptEvtValue,rptEvtVldty,rptEvtDateTime,rptEvtObjType,rptEvtParaLen,rptEvtPara }
        STATUS current
        DESCRIPTION
            "Packets per second of transmitted ethernet port, that is, number of actually transmitted packets/time unit."
        ::= { optixTrapsPM 682 }

    -- 1.3.6.1.4.1.2011.2.25.3.40.40.20.683
    pmETHRXTHROUGHPUTMAX NOTIFICATION-TYPE
        OBJECTS{ rptEvtPeriod,rptEvtValue,rptEvtVldty,rptEvtDateTime,rptEvtObjType,rptEvtParaLen,rptEvtPara }
        STATUS current
        DESCRIPTION
            "Maximum rate of packets including framing bits (20 bytes) and FCS bytes received by the port."
        ::= { optixTrapsPM 683 }

    -- 1.3.6.1.4.1.2011.2.25.3.40.40.20.684
    pmETHRXTHROUGHPUTMIN NOTIFICATION-TYPE
        OBJECTS{ rptEvtPeriod,rptEvtValue,rptEvtVldty,rptEvtDateTime,rptEvtObjType,rptEvtParaLen,rptEvtPara }
        STATUS current
        DESCRIPTION
            "Minimum rate of packets including framing bits (20 bytes) and FCS bytes received by the port."
        ::= { optixTrapsPM 684 }

    -- 1.3.6.1.4.1.2011.2.25.3.40.40.20.685
    pmETHRXTHROUGHPUTAVG NOTIFICATION-TYPE
        OBJECTS{ rptEvtPeriod,rptEvtValue,rptEvtVldty,rptEvtDateTime,rptEvtObjType,rptEvtParaLen,rptEvtPara }
        STATUS current
        DESCRIPTION
            "Average rate of packets including framing bits (20 bytes) and FCS bytes received by the port."
        ::= { optixTrapsPM 685 }

    -- 1.3.6.1.4.1.2011.2.25.3.40.40.20.686
    pmETHTXTHROUGHPUTMAX NOTIFICATION-TYPE
        OBJECTS{ rptEvtPeriod,rptEvtValue,rptEvtVldty,rptEvtDateTime,rptEvtObjType,rptEvtParaLen,rptEvtPara }
        STATUS current
        DESCRIPTION
            "Maximum rate of packets including framing bits (20 bytes) and FCS bytes transmitted by the port."
        ::= { optixTrapsPM 686 }

    -- 1.3.6.1.4.1.2011.2.25.3.40.40.20.687
    pmETHTXTHROUGHPUTMIN NOTIFICATION-TYPE
        OBJECTS{ rptEvtPeriod,rptEvtValue,rptEvtVldty,rptEvtDateTime,rptEvtObjType,rptEvtParaLen,rptEvtPara }
        STATUS current
        DESCRIPTION
            "Minimum rate of packets including framing bits (20 bytes) and FCS bytes transmitted by the port."
        ::= { optixTrapsPM 687 }

    -- 1.3.6.1.4.1.2011.2.25.3.40.40.20.688
    pmETHTXTHROUGHPUTAVG NOTIFICATION-TYPE
        OBJECTS{ rptEvtPeriod,rptEvtValue,rptEvtVldty,rptEvtDateTime,rptEvtObjType,rptEvtParaLen,rptEvtPara }
        STATUS current
        DESCRIPTION
            "Average rate of packets including framing bits (20 bytes) and FCS bytes transmitted by the port."
        ::= { optixTrapsPM 688 }
 -- 1.3.6.1.4.1.2011.2.25.3.40.40.20.692
    pmRXDROPRATIO NOTIFICATION-TYPE
        OBJECTS{ rptEvtPeriod,rptEvtValue,rptEvtVldty,rptEvtDateTime,rptEvtObjType,rptEvtParaLen,rptEvtPara }
        STATUS current
        DESCRIPTION
            "Packet loss ratio in the ingress direction"
        ::= { optixTrapsPM 692 }

    -- 1.3.6.1.4.1.2011.2.25.3.40.40.20.693
    pmTXDROPRATIO NOTIFICATION-TYPE
        OBJECTS{ rptEvtPeriod,rptEvtValue,rptEvtVldty,rptEvtDateTime,rptEvtObjType,rptEvtParaLen,rptEvtPara }
        STATUS current
        DESCRIPTION
            "Packet loss ratio in the egress direction"
        ::= { optixTrapsPM 693 }
    -- 1.3.6.1.4.1.2011.2.25.3.40.40.20.957
    pmRXBRDCASTRATIO NOTIFICATION-TYPE
        OBJECTS{ rptEvtPeriod,rptEvtValue,rptEvtVldty,rptEvtDateTime,rptEvtObjType,rptEvtParaLen,rptEvtPara }
        STATUS current
        DESCRIPTION
            "Ratio of broadcast and multicast packets to all packets in the receive direction."
        ::= { optixTrapsPM 957 }

    -- 1.3.6.1.4.1.2011.2.25.3.40.40.20.958
    pmTXBRDCASTRATIO NOTIFICATION-TYPE
        OBJECTS{ rptEvtPeriod,rptEvtValue,rptEvtVldty,rptEvtDateTime,rptEvtObjType,rptEvtParaLen,rptEvtPara }
        STATUS current
        DESCRIPTION
            "Ratio of broadcast and multicast packets to all packets in the transmit direction."
        ::= { optixTrapsPM 958 }

-- 1.3.6.1.4.1.2011.2.25.3.40.40.20.679
    pmRXBPS NOTIFICATION-TYPE
        OBJECTS{ rptEvtPeriod,rptEvtValue,rptEvtVldty,rptEvtDateTime,rptEvtObjType,rptEvtParaLen,rptEvtPara }
        STATUS current
        DESCRIPTION
            "Bits per second received."
        ::= { optixTrapsPM 679 }

-- 1.3.6.1.4.1.2011.2.25.3.40.40.20.681
    pmRXPPS NOTIFICATION-TYPE
        OBJECTS{ rptEvtPeriod,rptEvtValue,rptEvtVldty,rptEvtDateTime,rptEvtObjType,rptEvtParaLen,rptEvtPara }
        STATUS current
        DESCRIPTION
            "Packets per second received."
        ::= { optixTrapsPM 681 }

-- 1.3.6.1.4.1.2011.2.25.3.40.40.20.823
    pmRXPTPANNOUNCE NOTIFICATION-TYPE
        OBJECTS { rptEvtPeriod, rptEvtValue, rptEvtVldty, rptEvtDateTime, rptEvtObjType, rptEvtParaLen, rptEvtPara}
        STATUS current
        DESCRIPTION
            "Received ANNOUNCE Packet Count."
             ::= { optixTrapsPM 823 }

-- 1.3.6.1.4.1.2011.2.25.3.40.40.20.824
    pmTXPTPANNOUNCE NOTIFICATION-TYPE
        OBJECTS { rptEvtPeriod, rptEvtValue, rptEvtVldty, rptEvtDateTime, rptEvtObjType, rptEvtParaLen, rptEvtPara}
        STATUS current
        DESCRIPTION
            "Sent ANNOUNCE Packet Count."
             ::= { optixTrapsPM 824 }

-- 1.3.6.1.4.1.2011.2.25.3.40.40.20.825
    pmRXPTPSYNC NOTIFICATION-TYPE
        OBJECTS { rptEvtPeriod, rptEvtValue, rptEvtVldty, rptEvtDateTime, rptEvtObjType, rptEvtParaLen, rptEvtPara}
        STATUS current
        DESCRIPTION
            "Received SYNC Packet Count."
             ::= { optixTrapsPM 825 }

-- 1.3.6.1.4.1.2011.2.25.3.40.40.20.826
    pmTXPTPSYNC NOTIFICATION-TYPE
        OBJECTS { rptEvtPeriod, rptEvtValue, rptEvtVldty, rptEvtDateTime, rptEvtObjType, rptEvtParaLen, rptEvtPara}
        STATUS current
        DESCRIPTION
            "Sent SYNC Packet Count."
             ::= { optixTrapsPM 826 }

-- 1.3.6.1.4.1.2011.2.25.3.40.40.20.827
    pmRXPTPFOLLOWUP NOTIFICATION-TYPE
        OBJECTS { rptEvtPeriod, rptEvtValue, rptEvtVldty, rptEvtDateTime, rptEvtObjType, rptEvtParaLen, rptEvtPara}
        STATUS current
        DESCRIPTION
            "Received Follow_up Packet Count."
             ::= { optixTrapsPM 827 }

-- 1.3.6.1.4.1.2011.2.25.3.40.40.20.828
    pmTXPTPFOLLOWUP NOTIFICATION-TYPE
        OBJECTS { rptEvtPeriod, rptEvtValue, rptEvtVldty, rptEvtDateTime, rptEvtObjType, rptEvtParaLen, rptEvtPara}
        STATUS current
        DESCRIPTION
            "Sent Follow_up Packet Count."
             ::= { optixTrapsPM 828 }

-- 1.3.6.1.4.1.2011.2.25.3.40.40.20.829
    pmRXPTPDELAYREQ NOTIFICATION-TYPE
        OBJECTS { rptEvtPeriod, rptEvtValue, rptEvtVldty, rptEvtDateTime, rptEvtObjType, rptEvtParaLen, rptEvtPara}
        STATUS current
        DESCRIPTION
            "Received Delay_Req Packet Count."
             ::= { optixTrapsPM 829 }

-- 1.3.6.1.4.1.2011.2.25.3.40.40.20.830
    pmTXPTPDELAYREQ NOTIFICATION-TYPE
        OBJECTS { rptEvtPeriod, rptEvtValue, rptEvtVldty, rptEvtDateTime, rptEvtObjType, rptEvtParaLen, rptEvtPara}
        STATUS current
        DESCRIPTION
            "Sent Delay_Req Packet Count."
             ::= { optixTrapsPM 830 }

-- 1.3.6.1.4.1.2011.2.25.3.40.40.20.831
    pmRXPTPDELAYRESP NOTIFICATION-TYPE
        OBJECTS { rptEvtPeriod, rptEvtValue, rptEvtVldty, rptEvtDateTime, rptEvtObjType, rptEvtParaLen, rptEvtPara}
        STATUS current
        DESCRIPTION
            "Received Delay_Resp Packet Count."
             ::= { optixTrapsPM 831 }

-- 1.3.6.1.4.1.2011.2.25.3.40.40.20.832
    pmTXPTPDELAYRESP NOTIFICATION-TYPE
        OBJECTS { rptEvtPeriod, rptEvtValue, rptEvtVldty, rptEvtDateTime, rptEvtObjType, rptEvtParaLen, rptEvtPara}
        STATUS current
        DESCRIPTION
            "Sent Delay_Resp Packet Count."
             ::= { optixTrapsPM 832 }

-- 1.3.6.1.4.1.2011.2.25.3.40.40.20.833
    pmRXPTPPDELAYREQ NOTIFICATION-TYPE
        OBJECTS { rptEvtPeriod, rptEvtValue, rptEvtVldty, rptEvtDateTime, rptEvtObjType, rptEvtParaLen, rptEvtPara}
        STATUS current
        DESCRIPTION
            "Received Pdelay_Req Packet Count."
             ::= { optixTrapsPM 833 }

-- 1.3.6.1.4.1.2011.2.25.3.40.40.20.834
    pmTXPTPPDELAYREQ NOTIFICATION-TYPE
        OBJECTS { rptEvtPeriod, rptEvtValue, rptEvtVldty, rptEvtDateTime, rptEvtObjType, rptEvtParaLen, rptEvtPara}
        STATUS current
        DESCRIPTION
            "Sent Pdelay_Req Packet Count."
             ::= { optixTrapsPM 834 }

-- 1.3.6.1.4.1.2011.2.25.3.40.40.20.835
    pmRXPTPPDELAYRESP NOTIFICATION-TYPE
        OBJECTS { rptEvtPeriod, rptEvtValue, rptEvtVldty, rptEvtDateTime, rptEvtObjType, rptEvtParaLen, rptEvtPara}
        STATUS current
        DESCRIPTION
            "Received Pdelay_Resp Packet Count."
             ::= { optixTrapsPM 835 }

-- 1.3.6.1.4.1.2011.2.25.3.40.40.20.836
    pmTXPTPPDELAYRESP NOTIFICATION-TYPE
        OBJECTS { rptEvtPeriod, rptEvtValue, rptEvtVldty, rptEvtDateTime, rptEvtObjType, rptEvtParaLen, rptEvtPara}
        STATUS current
        DESCRIPTION
            "Sent Pdelay_Resp Packet Count."
             ::= { optixTrapsPM 836 }

-- 1.3.6.1.4.1.2011.2.25.3.40.40.20.837
    pmRXPTPPDELAYRESPFUP NOTIFICATION-TYPE
        OBJECTS { rptEvtPeriod, rptEvtValue, rptEvtVldty, rptEvtDateTime, rptEvtObjType, rptEvtParaLen, rptEvtPara}
        STATUS current
        DESCRIPTION
            "Received Pdelay_Resp_Follow_up Packt Count."
             ::= { optixTrapsPM 837 }

-- 1.3.6.1.4.1.2011.2.25.3.40.40.20.838
    pmTXPTPPDELAYRESPFUP NOTIFICATION-TYPE
        OBJECTS { rptEvtPeriod, rptEvtValue, rptEvtVldty, rptEvtDateTime, rptEvtObjType, rptEvtParaLen, rptEvtPara}
        STATUS current
        DESCRIPTION
            "Sent Pdelay_Resp_Follow_up Packet Count."
             ::= { optixTrapsPM 838 }

-- 1.3.6.1.4.1.2011.2.25.3.40.40.20.1
    pmOCPRXPKT64 NOTIFICATION-TYPE
        OBJECTS { rptEvtPeriod, rptEvtValue, rptEvtVldty, rptEvtDateTime, rptEvtObjType, rptEvtParaLen, rptEvtPara}
        STATUS current
        DESCRIPTION
            "Packets Received(64 Octets in Length)."
             ::= { optixTrapsPM 1 }

-- 1.3.6.1.4.1.2011.2.25.3.40.40.20.2
    pmOCPRXPKT65 NOTIFICATION-TYPE
        OBJECTS { rptEvtPeriod, rptEvtValue, rptEvtVldty, rptEvtDateTime, rptEvtObjType, rptEvtParaLen, rptEvtPara}
        STATUS current
        DESCRIPTION
            "Packets Received(65~127 Octets in Length)."
             ::= { optixTrapsPM 2 }

-- 1.3.6.1.4.1.2011.2.25.3.40.40.20.977
    pmVCGTXDROPPKTS NOTIFICATION-TYPE
        OBJECTS { rptEvtPeriod, rptEvtValue, rptEvtVldty, rptEvtDateTime, rptEvtObjType, rptEvtParaLen, rptEvtPara}
        STATUS current
        DESCRIPTION
            "VCG Tx dropped packets."
             ::= { optixTrapsPM 977 }

-- 1.3.6.1.4.1.2011.2.25.3.40.40.20.978
    pmVCGTXDROPRATIO NOTIFICATION-TYPE
        OBJECTS { rptEvtPeriod, rptEvtValue, rptEvtVldty, rptEvtDateTime, rptEvtObjType, rptEvtParaLen, rptEvtPara}
        STATUS current
        DESCRIPTION
            "VCG Tx packet loss rate."
             ::= { optixTrapsPM 978 }

-- 1.3.6.1.4.1.2011.2.25.3.40.40.20.981
    pmVCGRXDROPRATIO NOTIFICATION-TYPE
        OBJECTS { rptEvtPeriod, rptEvtValue, rptEvtVldty, rptEvtDateTime, rptEvtObjType, rptEvtParaLen, rptEvtPara}
        STATUS current
        DESCRIPTION
            "VCG Rx packet loss rate."
             ::= { optixTrapsPM 981 }

-- 1.3.6.1.4.1.2011.2.25.3.40.40.20.982
    pmVCGRXDROPPKTS NOTIFICATION-TYPE
        OBJECTS { rptEvtPeriod, rptEvtValue, rptEvtVldty, rptEvtDateTime, rptEvtObjType, rptEvtParaLen, rptEvtPara}
        STATUS current
        DESCRIPTION
            "VCG Rx dropped packets."
             ::= { optixTrapsPM 982 }

-- 1.3.6.1.4.1.2011.2.25.3.40.40.20.985
    pmVCGRXBWUTILIZATION NOTIFICATION-TYPE
        OBJECTS { rptEvtPeriod, rptEvtValue, rptEvtVldty, rptEvtDateTime, rptEvtObjType, rptEvtParaLen, rptEvtPara}
        STATUS current
        DESCRIPTION
            "received vcg bandwidth utilization."
             ::= { optixTrapsPM 985 }

-- 1.3.6.1.4.1.2011.2.25.3.40.40.20.986
    pmVCGRXBWUTILIZATIONMIN NOTIFICATION-TYPE
        OBJECTS { rptEvtPeriod, rptEvtValue, rptEvtVldty, rptEvtDateTime, rptEvtObjType, rptEvtParaLen, rptEvtPara}
        STATUS current
        DESCRIPTION
            "Minimum bandwidth utilization of the receive vcg."
             ::= { optixTrapsPM 986 }

-- 1.3.6.1.4.1.2011.2.25.3.40.40.20.987
    pmVCGRXBWUTILIZATIONAVG NOTIFICATION-TYPE
        OBJECTS { rptEvtPeriod, rptEvtValue, rptEvtVldty, rptEvtDateTime, rptEvtObjType, rptEvtParaLen, rptEvtPara}
        STATUS current
        DESCRIPTION
            "Average bandwidth utilization of the receive vcg."
             ::= { optixTrapsPM 987 }

-- 1.3.6.1.4.1.2011.2.25.3.40.40.20.988
    pmVCGRXBWUTILIZATIONMAX NOTIFICATION-TYPE
        OBJECTS { rptEvtPeriod, rptEvtValue, rptEvtVldty, rptEvtDateTime, rptEvtObjType, rptEvtParaLen, rptEvtPara}
        STATUS current
        DESCRIPTION
            "Maximum bandwidth utilization of the receive vcg."
             ::= { optixTrapsPM 988 }

-- 1.3.6.1.4.1.2011.2.25.3.40.40.20.989
    pmVCGTXBWUTILIZATION NOTIFICATION-TYPE
        OBJECTS { rptEvtPeriod, rptEvtValue, rptEvtVldty, rptEvtDateTime, rptEvtObjType, rptEvtParaLen, rptEvtPara}
        STATUS current
        DESCRIPTION
            "transmitted vcg bandwidth utilization."
             ::= { optixTrapsPM 989 }

-- 1.3.6.1.4.1.2011.2.25.3.40.40.20.990
    pmVCGTXBWUTILIZATIONMIN NOTIFICATION-TYPE
        OBJECTS { rptEvtPeriod, rptEvtValue, rptEvtVldty, rptEvtDateTime, rptEvtObjType, rptEvtParaLen, rptEvtPara}
        STATUS current
        DESCRIPTION
            "Minimum bandwidth utilization of the transmitted vcg."
             ::= { optixTrapsPM 990 }

-- 1.3.6.1.4.1.2011.2.25.3.40.40.20.991
    pmVCGTXBWUTILIZATIONAVG NOTIFICATION-TYPE
        OBJECTS { rptEvtPeriod, rptEvtValue, rptEvtVldty, rptEvtDateTime, rptEvtObjType, rptEvtParaLen, rptEvtPara}
        STATUS current
        DESCRIPTION
            "Average bandwidth utilization of the transmitted vcg."
             ::= { optixTrapsPM 991 }

-- 1.3.6.1.4.1.2011.2.25.3.40.40.20.992
    pmVCGTXBWUTILIZATIONMAX NOTIFICATION-TYPE
        OBJECTS { rptEvtPeriod, rptEvtValue, rptEvtVldty, rptEvtDateTime, rptEvtObjType, rptEvtParaLen, rptEvtPara}
        STATUS current
        DESCRIPTION
            "Maximum bandwidth utilization of the transmitted vcg."
             ::= { optixTrapsPM 992 }

    END                                                                                                      
                                                                                                               
--                                                                                                             
-- OPTIX-GLOBAL-PM-TRAPS-Mstp-MIB.my                                                                            
--
