--
-- OPTIX-WDM-FUNCTION-MIB.mib
-- Tuesday, January 5, 2021 at 11:23:35
--
-- =================================================================
-- Copyright (C) 2021 by HUAWEI TECHNOLOGIES. All rights reserved
-- Description:
-- Reference:
-- Version: V1.00
-- History:
-- <author>,<date>,<contents>
-- =================================================================

	OPTIX-WDM-FUNCTION-MIB DEFINITIONS ::= BEGIN
 
		IMPORTS
			optixProvisionWDM			
				FROM OPTIX-OID-MIB			
			OBJECT-TYPE			
				FROM SNMPv2-SMI;
	
	
--
-- Node definitions
--
	
		-- 1.3.6.1.4.1.2011.2.25.4.70.10
		optixWDMFunction OBJECT IDENTIFIER ::= { optixProvisionWDM 10 }
		
		-- 1.3.6.1.4.1.2011.2.25.4.70.10.10
		optixWDMBdFunction OBJECT IDENTIFIER ::= { optixWDMFunction 10 }
		
		-- 1.3.6.1.4.1.2011.2.25.4.70.10.10.10
		optixWDMGetBdInfoTable OBJECT-TYPE
			SYNTAX SEQUENCE OF OptixWDMGetBdInfoEntry
			MAX-ACCESS not-accessible
			STATUS current
			DESCRIPTION
				"Table for querying board manufacture information."
			::= { optixWDMBdFunction 10 }
		
		-- 1.3.6.1.4.1.2011.2.25.4.70.10.10.10.1
		optixWDMGetBdInfoEntry OBJECT-TYPE
			SYNTAX OptixWDMGetBdInfoEntry
			MAX-ACCESS not-accessible
			STATUS current
			DESCRIPTION
				"Description."
			INDEX { optixWDMGetBdInfoBID }
			::= { optixWDMGetBdInfoTable 1 }
		
		OptixWDMGetBdInfoEntry ::=
			SEQUENCE { 
				optixWDMGetBdInfoBID
					OCTET STRING,
				optixWDMGetBdInfoData
					OCTET STRING
			 }

		-- 1.3.6.1.4.1.2011.2.25.4.70.10.10.10.1.1
		optixWDMGetBdInfoBID OBJECT-TYPE
			SYNTAX OCTET STRING (SIZE (0..8))
			MAX-ACCESS read-only
			STATUS current
			DESCRIPTION
				"Board ID."
			::= { optixWDMGetBdInfoEntry 1 }
		
		-- 1.3.6.1.4.1.2011.2.25.4.70.10.10.10.1.2
		optixWDMGetBdInfoData OBJECT-TYPE
			SYNTAX OCTET STRING (SIZE (0..9740))
			MAX-ACCESS read-only
			STATUS current
			DESCRIPTION
				"Board Information."
			::= { optixWDMGetBdInfoEntry 2 }

		-- 1.3.6.1.4.1.2011.2.25.4.70.10.10.20
		optixGetPortInfoTable OBJECT-TYPE
			SYNTAX SEQUENCE OF OptixGetPortInfoEntry
			MAX-ACCESS not-accessible
			STATUS current
			DESCRIPTION
				"Table for querying board port information."
			::= { optixWDMBdFunction 20 }

		-- 1.3.6.1.4.1.2011.2.25.4.70.10.10.20.1
		optixGetPortInfoEntry OBJECT-TYPE
			SYNTAX OptixGetPortInfoEntry
			MAX-ACCESS not-accessible
			STATUS current
			DESCRIPTION
				"This entry describes the information about all ports on the NE."
			INDEX { optixGetBidAndBdtype,optixGetPortInfoPort }
			::= { optixGetPortInfoTable 1 }

		OptixGetPortInfoEntry ::=
			SEQUENCE {
			     optixGetBidAndBdtype
					OCTET STRING,
			     optixGetPortInfoPort
					INTEGER,
				 optixGetPortInfoType
					INTEGER,
				 optixGetPortInfoWorkMode
					INTEGER,
				 optixGetPortInfoPaylodType
					INTEGER,
				 optixGetPortInfoName
					OCTET STRING
			 }

		-- 1.3.6.1.4.1.2011.2.25.4.70.10.10.20.1.1
			   optixGetBidAndBdtype OBJECT-TYPE
			        SYNTAX OCTET STRING (SIZE (0..40))
			        MAX-ACCESS read-only
			        STATUS current
			        DESCRIPTION
				       "Board slot ID and board type."
			        ::= { optixGetPortInfoEntry 1 }

		-- 1.3.6.1.4.1.2011.2.25.4.70.10.10.20.1.2
                optixGetPortInfoPort OBJECT-TYPE
                      SYNTAX INTEGER (0..255)
                      MAX-ACCESS read-only
                      STATUS current
                      DESCRIPTION
                            "Port ID"
                      ::= { optixGetPortInfoEntry 2 }

		-- 1.3.6.1.4.1.2011.2.25.4.70.10.10.20.1.3
                optixGetPortInfoType OBJECT-TYPE
                SYNTAX INTEGER
                {
                    oport(1),
                    eport(2),
                    cbwport(6),
                    ccport(7),
                    lcport(8),
                    ceport(9),
                    lbwport(10),
                    lcport-fixed(11),
                    voaport(12),
                    oscport(13),
                    wdm4port(14),
                    wdm10port(15),
                    cfp4x10g(16),
                    cfp4x25g(17),
                    cfp10x10g(18),
                    cxp10x10g(19),
                    lcmport(21),
                    cfp4x28g(22),
                    qsfp4x28g(24),
                    qsfp4x10g(25),
                    wdminport(26),
                    wdmoutport(27),
                    wdminoutport(28),
                    clockport(34),
                    cxp12x25g(36),
                    lane8x56g(37),
                    lane4x112g(38),
                    lane4x56g(39),
                    lane8x10g(40),
                    flexeport(41),
                    sfp28port(42),
                    qsfp2x28g(43),
                    lane2x4x28g(44),
                    unknow(254),
               }
               MAX-ACCESS read-only
               STATUS current
               DESCRIPTION
                   "Port type"
              ::= { optixGetPortInfoEntry 3 }

		-- 1.3.6.1.4.1.2011.2.25.4.70.10.10.20.1.4
            optixGetPortInfoWorkMode OBJECT-TYPE
                SYNTAX INTEGER
                {
                  t-odu0(0),
                  t-any-odu0-nocross(1),
                  t-odu0-odu1(2),
                  t-odu1(256),
                  t-odu1odu0(257),
                  t-odu1anyodu0(258),
                  t-odu1anyodu0odu1(259),
                  t-any-odu1-cross(260),
                  t-any-odu1-nocross(261),
                  t-any-odu2(512),
                  t-any-odu3_nocross(513),
                  t-any-odu4(514),
                  t-any-oduflex(2560),
                  t1-odu0(4096),
                  t-any-odu0-odu1-otu2(4097),
                  tl-odu1anyodu0odu1(4352),
                  tl-odu1(4353),
                  t-any-odu1-otu2(4354),
                  t-otu1-odu0-odu1-otu2(4355),
                  t-any-otu2(4608),
                  t-any-odu2-otu4(4612),
                  t-4xany-4xodu2(4613),
                  t-4xany-4xoduflex(4614),
                  t-8xany-odu2(4615),
                  t-2xany-oduflex-trunk(4616),
                  t-4xany-oduflex-trunk(4617),
                  t-8xany-oduflex-trunk(4618),
                  t-any-oduflex-otu2(6656),
                  t-any-oduflex-otu4(6660),
                  t-general-line-mode(57345),
                  t-general-optrelay-mode(57346),
                  t-general-elecrelay-mode(57347),
                  t-general-branch-mode(57348),
                  t-sdh-line-mode(57349),
                  t-odu1-sdh-mode(57350),
                  t-any-oduflex-4v(57351),
                  t-any-oduflex-2v(57352),
                  t-any-2xodu4(57353),
                  t-any-2xodu4-tduflex(57360),
                  t-any-tduflex(57361),
                  t-bidirectional-elecrelay-mode(57362),
                  t-bidirectional-optrelay-mode(57363),
                  t-flexe(63489),
                  none(65535),
               }
               MAX-ACCESS read-only
               STATUS current
               DESCRIPTION
                   "Port working mode"
              ::= { optixGetPortInfoEntry 4 }

	    -- 1.3.6.1.4.1.2011.2.25.4.70.10.10.20.1.5
            optixGetPortInfoPaylodType OBJECT-TYPE
                SYNTAX INTEGER
                {
                    none(0),
                    ge(257),
                    gelan10(258),
                    gewan10(259),
                    fe(260),
                    ge-gfp-t(261),
                    getttagmp(263),
                    ge40(264),
                    gelan100(265),
                    otu1(513),
                    otu2(514),
                    otu3(515),
                    otu5g(516),
                    otu3e(517),
                    otu2e(518),
                    otu4(521),
                    odu0(528),
                    odu1(529),
                    odu2(530),
                    odu3(531),
                    odu4(533),
                    oduflex(534),
                    stm1(769),
                    stm4(770),
                    stm16(771),
                    stm64(772),
                    stm256(773),
                    oc3(1025),
                    oc12(1026),
                    oc48(1027),
                    oc192(1028),
                    oc768(1029),
                    fc50(1281),
                    fc100(1282),
                    fc200(1283),
                    fc400(1284),
                    fc1000(1285),
                    gefc10(1286),
                    fc800(1289),
                    fc1600(1290),
                    fc3200(1291),
                    ficon(1537),
                    ficonex(1538),
                    ficon4g(1539),
                    ficon8g(1541),
                    ficon10g(1544),
                    hdsdi(1793),
                    hdsdi-na(1794),
                    gsdi(1795),
                    gsdi-na(1796),
                    dvbasi(2049),
                    sdi(2050),
                    escon(2305),
                    fddi(2561),
                    etr(2817),
                    clo(2818),
                    isc1g(2819),
                    isc2g(2820),
                    infinibandsdr(3073),
                    infinibandddr(3074),
                    ibqdr(3075),
                    cpri2(3329),
                    cpri1(3330),
                    cpri3(3331),
                    cpri4(3332),
                    cpri5(3333),
                    cpri6(3334),
                    cpri7(3335),
                    obsai4(3336),
                    obsai8(3337),
                    cpri8(3338),
                    obsai2(3339),
                    fc4x1600(3340),
                    fc4x3200(3341),
                    gelan25(3344),
                    gelan400(3350),
                    ge400-4v(3351),
                    ge50(3352),
                    gelan200(3353),
                    ge200-2v(3354),
                    fc3200-trunk-2(3355),
                    fc3200-trunk-4(3356),
                    fc1600-trunk-2(3357),
                    fc1600-trunk-4(3358),
                    fc1600-trunk-8(3359),
                    fc1200-trunk-2(3360),
                    fc1200-trunk-4(3361),
                    fc1200-trunk-8(3362),
                    fc800-trunk-2(3363),
                    fc800-trunk-4(3364),
                    fc800-trunk-8(3365),
                    flexe-aware(3366),
                    cbr10g(3585),
                    packet(3841),
                    custom(65281),
                    any(65535),
               }
               MAX-ACCESS read-only
               STATUS current
               DESCRIPTION
                   "Port payload type"
              ::= { optixGetPortInfoEntry 5 }

	    -- 1.3.6.1.4.1.2011.2.25.4.70.10.10.20.1.6
		    optixGetPortInfoName OBJECT-TYPE
			   SYNTAX OCTET STRING (SIZE (0..64))
			   MAX-ACCESS read-write
			   STATUS current
			   DESCRIPTION
				   "Port name"
			   ::= { optixGetPortInfoEntry 6 }

		-- 1.3.6.1.4.1.2011.2.25.4.70.10.10.30
		optixGetPortStateTable OBJECT-TYPE
			   SYNTAX SEQUENCE OF OptixGetPortStateEntry
			   MAX-ACCESS not-accessible
			   STATUS current
			   DESCRIPTION
				   "Table for querying board port status"
			   ::= { optixWDMBdFunction 30 }

		-- 1.3.6.1.4.1.2011.2.25.4.70.10.10.30.1
		optixGetPortStateEntry OBJECT-TYPE
			    SYNTAX OptixGetPortStateEntry
			    MAX-ACCESS not-accessible
			    STATUS current
			    DESCRIPTION
				    "This entry describes the configuration of port status"
			    INDEX { optixGetBidAndBdtype,optixLogSubCardId,optixGetPortStatusPort }
			    ::= { optixGetPortStateTable 1 }

		OptixGetPortStateEntry ::=
			 SEQUENCE {
			     optixGetBid
					OCTET STRING,
			     optixGetPortStatePort
					INTEGER,
				 optixGetPortState
					OCTET STRING
			 }

	    -- 1.3.6.1.4.1.2011.2.25.4.70.10.10.30.1.1
	    optixGetBid OBJECT-TYPE
			          SYNTAX OCTET STRING (SIZE (0..8))
			          MAX-ACCESS read-only
			          STATUS current
			          DESCRIPTION
				           "Board slot ID"
			          ::= { optixGetPortStateEntry 1 }

        -- 1.3.6.1.4.1.2011.2.25.4.70.10.10.30.1.2
        optixGetPortStatePort OBJECT-TYPE
                      SYNTAX INTEGER (0..255)
                      MAX-ACCESS read-only
                      STATUS current
                      DESCRIPTION
                            "Port ID"
                      ::= { optixGetPortStateEntry 2 }

	    -- 1.3.6.1.4.1.2011.2.25.4.70.10.10.30.1.3
        optixGetPortState OBJECT-TYPE
                      SYNTAX OCTET STRING (SIZE (0..32))
                      MAX-ACCESS read-only
                      STATUS current
                      DESCRIPTION
                            "Port status"
                      ::= { optixGetPortStateEntry 3 }
			
		-- 1.3.6.1.4.1.2011.2.25.4.70.20
		optixWDMDeviceMgr OBJECT IDENTIFIER ::= { optixProvisionWDM 20 }
		
		-- 1.3.6.1.4.1.2011.2.25.4.70.20.10
		optixWDMFanMgr OBJECT IDENTIFIER ::= { optixWDMDeviceMgr 10 }
		
		-- 1.3.6.1.4.1.2011.2.25.4.70.20.10.10
		optixWDMFanTable OBJECT-TYPE
			SYNTAX SEQUENCE OF OptixWDMFanEntry
			MAX-ACCESS not-accessible
			STATUS current
			DESCRIPTION
				"Table for querying Fan speed information."
			::= { optixWDMFanMgr 10 }
			
		-- 1.3.6.1.4.1.2011.2.25.4.70.20.10.10.1
		optixWDMFanEntry OBJECT-TYPE
			SYNTAX OptixWDMFanEntry
			MAX-ACCESS not-accessible
			STATUS current
			DESCRIPTION
				"Table for query Fan speed information."
			INDEX { optixWDMGetFanBID }
			::= { optixWDMFanTable 1 }
		
		OptixWDMFanEntry ::=
			SEQUENCE { 
				optixWDMGetFanBID
					INTEGER,
				optixWDMGetFanSpeed
					INTEGER
			 }

		-- 1.3.6.1.4.1.2011.2.25.4.70.20.10.10.1.1
		optixWDMGetFanBID OBJECT-TYPE
			SYNTAX INTEGER (0..65535)
			MAX-ACCESS read-only
			STATUS current
			DESCRIPTION
				"Fan board slot ID."
			::= { optixWDMFanEntry 1 }
		
		-- 1.3.6.1.4.1.2011.2.25.4.70.20.10.10.1.2
		optixWDMGetFanSpeed OBJECT-TYPE
			SYNTAX INTEGER
				{
				low(1),
				mid(2),
				high(3),
				stop(4),
				auto-low(5),
				auto-mid(6),
				auto-high(7),
				auto(9),
				mid-low(10),
				mid-high(11),
				}
			MAX-ACCESS read-only
			STATUS current
			DESCRIPTION
				"Current Fan speed."
			::= { optixWDMFanEntry 2 }

		-- 1.3.6.1.4.1.2011.2.25.4.70.20.20
		optixWDMPsuMgr OBJECT IDENTIFIER ::= { optixWDMDeviceMgr 20 }
		
		-- 1.3.6.1.4.1.2011.2.25.4.70.20.20.10
		optixWDMPsuTable OBJECT-TYPE
			SYNTAX SEQUENCE OF OptixWDMPsuEntry
			MAX-ACCESS not-accessible
			STATUS current
			DESCRIPTION
				"Table for querying power save information."
			::= { optixWDMPsuMgr 10 }
			
		-- 1.3.6.1.4.1.2011.2.25.4.70.20.20.10.1
		optixWDMPsuEntry OBJECT-TYPE
			SYNTAX OptixWDMPsuEntry
			MAX-ACCESS not-accessible
			STATUS current
			DESCRIPTION
				"Table for query power save information."
			INDEX { optixWDMGetPsuBID }
			::= { optixWDMPsuTable 1 }
		
		OptixWDMPsuEntry ::=
			SEQUENCE { 
				optixWDMGetPsuBID
					INTEGER,
				optixWDMGetPsuPowerConsumption
					INTEGER
			 }

		-- 1.3.6.1.4.1.2011.2.25.4.70.20.20.10.1.1
		optixWDMGetPsuBID OBJECT-TYPE
			SYNTAX INTEGER (0..65535)
			MAX-ACCESS read-only
			STATUS current
			DESCRIPTION
				"Piu board slot ID."
			::= { optixWDMPsuEntry 1 }
		
		-- 1.3.6.1.4.1.2011.2.25.4.70.20.20.10.1.2
		optixWDMGetPsuPowerConsumption OBJECT-TYPE
			SYNTAX INTEGER (0..65535)
			MAX-ACCESS read-only
			STATUS current
			DESCRIPTION
				"Current psu power consumption."
			::= { optixWDMPsuEntry 2 }
	END

--
-- 10_OPTIX-WDM-FUNCTION-MIB.mib9.173.22.198
--
