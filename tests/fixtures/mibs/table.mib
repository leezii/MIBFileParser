-- TABLE-MIB
-- MIB file with table structure for testing

TABLE-TEST-MIB DEFINITIONS ::= BEGIN

IMPORTS
    OBJECT-TYPE
        FROM SNMPv2-SMI
    Integer32, DisplayString
        FROM SNMPv2-TC;

-- Root OID
tableTest OBJECT IDENTIFIER ::= { 1 3 6 1 4 1 9998 }

-- Interface table
ifTable OBJECT-TYPE
    SYNTAX      SEQUENCE OF IfEntry
    MAX-ACCESS  not-accessible
    STATUS      current
    DESCRIPTION "A list of interface entries"
    ::= { tableTest 1 }

ifEntry OBJECT-TYPE
    SYNTAX      IfEntry
    MAX-ACCESS  not-accessible
    STATUS      current
    DESCRIPTION "An interface entry"
    INDEX       { ifIndex }
    ::= { ifTable 1 }

IfEntry ::= SEQUENCE {
    ifIndex     Integer32,
    ifDescr     DisplayString,
    ifType      Integer32,
    ifSpeed     Integer32
}

ifIndex OBJECT-TYPE
    SYNTAX      Integer32 (1..2147483647)
    MAX-ACCESS  read-only
    STATUS      current
    DESCRIPTION "A unique value for each interface"
    ::= { ifEntry 1 }

ifDescr OBJECT-TYPE
    SYNTAX      DisplayString
    MAX-ACCESS  read-only
    STATUS      current
    DESCRIPTION "A textual string containing information about the interface"
    ::= { ifEntry 2 }

ifType OBJECT-TYPE
    SYNTAX      Integer32
    MAX-ACCESS  read-only
    STATUS      current
    DESCRIPTION "The type of interface"
    ::= { ifEntry 3 }

ifSpeed OBJECT-TYPE
    SYNTAX      Integer32
    MAX-ACCESS  read-only
    STATUS      current
    DESCRIPTION "An estimate of the interface's current bandwidth"
    ::= { ifEntry 4 }

END
