-- SNMPv2-CONF.mib
-- SNMPv2 Configuration definitions

SNMPv2-CONF DEFINITIONS ::= BEGIN

IMPORTS
    OBJECT-TYPE, MODULE-IDENTITY, Integer32
        FROM SNMPv2-SMI;

-- SNMPv2 Configuration Module Identity
snmpMIB OBJECT IDENTIFIER ::= { 1 3 6 1 6 3 1 }

snmpMIBObjects OBJECT IDENTIFIER ::= { snmpMIB 1 }

-- Basic configuration groups
snmpSystem OBJECT IDENTIFIER ::= { snmpMIBObjects 1 }
snmpParameters OBJECT IDENTIFIER ::= { snmpMIBObjects 2 }

END
