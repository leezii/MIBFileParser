-- SIMPLE-MIB
-- Simple MIB file for testing

SIMPLE-MIB DEFINITIONS ::= BEGIN

IMPORTS
    OBJECT-GROUP
        FROM SNMPv2-CONF
    Integer32, OBJECT-TYPE
        FROM SNMPv2-SMI
    DisplayString
        FROM SNMPv2-TC;

-- Root OID
simpleTest OBJECT IDENTIFIER ::= { 1 3 6 1 4 1 9999 }

-- Simple scalar objects
sysDescr OBJECT-TYPE
    SYNTAX      DisplayString
    MAX-ACCESS  read-only
    STATUS      current
    DESCRIPTION "A simple system description"
    ::= { simpleTest 1 }

sysVersion OBJECT-TYPE
    SYNTAX      DisplayString
    MAX-ACCESS  read-only
    STATUS      current
    DESCRIPTION "System version string"
    ::= { simpleTest 2 }

sysStatus OBJECT-TYPE
    SYNTAX      Integer32 (0..255)
    MAX-ACCESS  read-only
    STATUS      current
    DESCRIPTION "System status code"
    ::= { simpleTest 3 }

END
