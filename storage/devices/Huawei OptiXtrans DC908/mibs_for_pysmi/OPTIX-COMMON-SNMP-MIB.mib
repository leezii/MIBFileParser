-- OPTIX-COMMON-SNMP-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-COMMON-SNMP-MIB DEFINITIONS ::= BEGIN
    IMPORTS
        optixCommonSnmp
            FROM OPTIX-OID-MIB
        OBJECT-GROUP,MODULE-COMPLIANCE
            FROM SNMPv2-CONF
        OBJECT-TYPE,MODULE-IDENTITY,NOTIFICATION-TYPE
            FROM SNMPv2-SMI
        ;

    optixSnmp MODULE-IDENTITY
        LAST-UPDATED "201411251033Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "SNMP interface module"
        REVISION "201411251033Z"
        DESCRIPTION
            "The initial version"
        ::={ optixCommonSnmp 10 }

    -- 1.3.6.1.4.1.2011.2.25.3.1.10.1
    optixSnmpTrap OBJECT IDENTIFIER ::= { optixSnmp 1 }


END
